Attribute VB_Name = "AcToolsLightHole"
Option Explicit

Private HD_WD As Double          'maximum hole depth as a fraction ofweb depth
Private HL_SP As Double          'maximum hole length as a fraction of spacing
Private HL_WD As Double          'maximum hole length as a fraction of web depth
Private CR_HD As Double          'minimum corner radius as a fraction of hole depth
Private AlignUCS As Boolean      'align with UCS or with the Web direction
Private sLayerName As String     'destination layer for the hole geometry

Private Enum WebDirection
    Vertical
    Horizontal
    Skewed
End Enum

Public Sub CTLightHole()
    Dim selSet As AcadSelectionSet
    Dim cLines As Collection
 
    If ThisDrawing.ActiveSpace = acPaperSpace Then
        ThisDrawing.Utility.Prompt "Unable to run the command. Please, switch to the Model space and try again." & vbLf
        Exit Sub
    End If
            
    Set selSet = ThisDrawing.PickfirstSelectionSet
    ObtainLinesFromSelectionSet selSet, cLines
    
    If cLines.Count = 0 Then
        While ThisDrawing.SelectionSets.Count > 0
            ThisDrawing.SelectionSets(0).Delete
        Wend
        Set selSet = ThisDrawing.SelectionSets.Add("selSet")
        If Not SelectOrDrawReferenceLines(selSet, cLines) Then
            GoTo errCancelOperation
        End If
        
        ObtainLinesFromSelectionSet selSet, cLines
    End If
    
    If cLines.Count = 0 Then
        GoTo errCancelOperation
    End If
    
    If ConfirmGenerate(selSet, cLines) Then
        GenerateGeometry cLines
    Else
        GoTo errCancelOperation
    End If
    
    If DeleteReferenceLines(cLines) Then Exit Sub

errCancelOperation:
    If Not selSet Is Nothing Then
        If selSet.Name = "selSet" Then
            selSet.Highlight False
            selSet.Delete
        End If
    End If
End Sub

Private Function ConfirmGenerate(ByRef selSet As AcadSelectionSet, ByRef cLines As Collection) As Boolean
    Dim sResult As String
    Dim uf As ufLHoleOptions
    Dim c As Collection
    
    Set c = LoadSettings_CTLightHole()
    If Not ValidateSettings(c) Then
         WarningMsg "The saved settings file is corrupted. Default parameters will be applied."
        Set c = LoadSettings_CTLightHole(True)
    End If
    
    If c.Count > 1 Then HD_WD = c(2) / 100
    If c.Count > 2 Then HL_SP = c(3) / 100
    If c.Count > 3 Then HL_WD = c(4) / 100
    If c.Count > 4 Then CR_HD = c(5) / 100
    If c.Count > 5 Then AlignUCS = Not CBool(c(6))
    If c.Count > 6 Then sLayerName = c(7)
    
    ThisDrawing.Utility.InitializeUserInput 0, "Generate Options Align"
    
    If cLines.Count < 2 Then
        ThisDrawing.Utility.Prompt ("At least two reference lines need to be selected to create a lightening hole." & vbLf)
        GoTo errCancelOperation
    End If
    
    On Error GoTo errCancelOperation
    If AlignUCS Then
        sResult = ThisDrawing.Utility.GetKeyword("Generate lightening hole geometry? [<Generate>/Options/Alignment (set to UCS)]:")
    Else
        sResult = ThisDrawing.Utility.GetKeyword("Generate lightening hole geometry? [<Generate>/Options/Alignment (set to Web)]:")
    End If
    On Error GoTo 0
    If sResult = "" Then sResult = "Generate"
    
    Select Case sResult
        Case "Align"
            If c.Count > 5 Then
                c.Remove (6)
                c.Add AlignUCS, , , 5
                SaveSettings_CTLightHole c
            End If
            ConfirmGenerate = ConfirmGenerate(selSet, cLines)
            Exit Function
        Case "Options"
            Set uf = New ufLHoleOptions
            uf.show
            Unload uf
            ConfirmGenerate = ConfirmGenerate(selSet, cLines)
            Exit Function
        Case "Generate"
            ConfirmGenerate = True
    End Select
         
    Exit Function
    
errCancelOperation:
    ConfirmGenerate = False
End Function

Private Function ValidateSettings(ByRef c As Collection) As Boolean
    Dim i As Integer
    Dim v As Variant
    If c.Count > 1 Then
        i = 2
        On Error GoTo errValidateFail
        v = CDbl(c(i))
        On Error GoTo 0
    End If
    If c.Count > 2 Then
        i = 3
        On Error GoTo errValidateFail
        v = CDbl(c(i))
        On Error GoTo 0
    End If
    If c.Count > 3 Then
        i = 4
        On Error GoTo errValidateFail
        v = CDbl(c(i))
        On Error GoTo 0
    End If
    If c.Count > 4 Then
        i = 5
        On Error GoTo errValidateFail
        v = CDbl(c(i))
        On Error GoTo 0
    End If
    If c.Count > 5 Then
        i = 6
        On Error GoTo errValidateFail
        v = CBool(c(6))
        On Error GoTo 0
    End If
    
    ValidateSettings = True
    Exit Function

errValidateFail:
    ValidateSettings = False
End Function

Private Function SelectOrDrawReferenceLines(ByRef selSet As AcadSelectionSet, ByRef cLines As Collection) As Boolean
    Dim sResult As String
            
    ThisDrawing.Utility.InitializeUserInput 0, "Select Draw"
    On Error GoTo errCancelOperation
        sResult = ThisDrawing.Utility.GetKeyword("Select or draw reference lines [<Select>/Draw]:")
        If sResult = "" Then sResult = "Select"
    On Error GoTo 0
        
    Select Case sResult
        Case "Select"
            selSet.SelectOnScreen
            ObtainLinesFromSelectionSet selSet, cLines
        Case "Draw"
            If Not DrawLineAndAddToSelectionSet(selSet, "the web depth reference line") Then
                GoTo errCancelOperation
            End If
            If Not DrawLineAndAddToSelectionSet(selSet, "the spacing reference line") Then
                GoTo errCancelOperation
            End If
    End Select
    
    SelectOrDrawReferenceLines = True
    Exit Function
    
errCancelOperation:
    SelectOrDrawReferenceLines = False
End Function

Private Function DrawLineAndAddToSelectionSet(ByRef selSet As AcadSelectionSet, sLineName As String) As Boolean
    Dim pt1 As Variant
    Dim pt2 As Variant
    Dim objs(0 To 0) As AcadEntity
    Dim ln As AcadLine
    Dim acPt As AcadPoint
    Dim bIsModelSpace As Boolean
    Dim nLastCount As Long
    
    If ThisDrawing.ActiveSpace = acModelSpace Then
        bIsModelSpace = True
        nLastCount = ThisDrawing.ModelSpace.Count
    Else
        bIsModelSpace = False
        nLastCount = ThisDrawing.PaperSpace.Count
    End If
    
    
    On Error GoTo errCancelOperation
    pt1 = ThisDrawing.Utility.GetPoint(, "Select the first point of " & sLineName & ":")
    Set acPt = ThisDrawing.ModelSpace.AddPoint(pt1)
    pt2 = ThisDrawing.Utility.GetPoint(, "Select the second point of " & sLineName & ":")
    acPt.Delete
    On Error GoTo 0
                           
    Set ln = ThisDrawing.ModelSpace.AddLine(pt1, pt2)
    Set objs(0) = ln
    selSet.AddItems objs
        
    selSet.Highlight True
    DrawLineAndAddToSelectionSet = True
    Exit Function
    
errCancelOperation:
    DrawLineAndAddToSelectionSet = False
    If Not acPt Is Nothing Then
        acPt.Delete
    End If
End Function

Private Function ObtainLinesFromSelectionSet(ByRef selSet As AcadSelectionSet, ByRef cLines As Collection)
    Dim ent As AcadEntity
    
    Set cLines = New Collection
        
    For Each ent In selSet
        If LCase(TypeName(ent)) = "iacadline" Then
            cLines.Add ent
        End If
    Next ent
End Function

Private Function DeleteReferenceLines(cLines As Collection) As Boolean
    Dim sResult As String
    Dim ln As AcadLine
    
    If cLines.Count = 0 Then
        GoTo errCancelOperation
    End If
            
    ThisDrawing.Utility.InitializeUserInput 0, "Keep Delete"
    On Error GoTo errCancelOperation
        sResult = ThisDrawing.Utility.GetKeyword("Keep reference lines? [<Keep>/Delete]:")
        If sResult = "" Then sResult = "Keep"
    On Error GoTo 0
    
    Select Case sResult
        Case "Delete"
            For Each ln In cLines
                ln.Delete
            Next ln
            DeleteReferenceLines = True
            
        Case "Keep"
            DeleteReferenceLines = False
    End Select
    Exit Function
    
errCancelOperation:
    DeleteReferenceLines = False
End Function

Private Function GenerateGeometry(cLines As Collection) As Boolean
    Dim lnWeb As AcadLine
    Dim lnSpacing As AcadLine
    Dim sResult As String
    Dim i As Integer
            
    If cLines.Count = 0 Then
        ThisDrawing.Utility.Prompt "Unable to create holes. Reference lines are not selected." & vbLf
        GenerateGeometry = False
        Exit Function
    End If
    
    If (Int(cLines.Count / 2)) * 2 <> cLines.Count Then
        ThisDrawing.Utility.Prompt "Unable to create holes. Selected lines are not provided in pairs." & vbLf
        GenerateGeometry = False
        Exit Function
    End If
    
    For i = 1 To cLines.Count Step 2
        Set lnWeb = cLines(i)
        Set lnSpacing = cLines(i + 1)
        GenerateGeometryForCurrentHole lnWeb, lnSpacing
    Next i
                
    GenerateGeometry = True
End Function


Private Function GenerateGeometryForCurrentHole(lnWeb As AcadLine, lnSpacing As AcadLine) As AcadPolyline
    Dim pln As AcadPolyline
    Dim pts(0 To 23) As Double
    Dim w1 As Variant
    Dim w2 As Variant
    Dim s1 As Variant
    Dim s2 As Variant
    Dim HD As Double 'hole depth
    Dim HL As Double 'hole lenght
    Dim CR As Double
    Dim ang As Double
    Dim dx As Double
    Dim dy As Double
    Dim i As Integer
    Dim wd As Double
    Dim sp As Double
    Dim WebDir As WebDirection
    Dim kw As Double
    Dim bw As Double
    Dim ks1 As Double
    Dim ks2 As Double
    Dim bs1 As Double
    Dim bs2 As Double
           
    'convert coordinates of web line ends from WCS to UCS
    w1 = ThisDrawing.Utility.TranslateCoordinates(lnWeb.StartPoint, acWorld, acUCS, False)
    w2 = ThisDrawing.Utility.TranslateCoordinates(lnWeb.EndPoint, acWorld, acUCS, False)
      
    
    'convert coordinates of web line ends from WCS to UCS
    s1 = ThisDrawing.Utility.TranslateCoordinates(lnSpacing.StartPoint, acWorld, acUCS, False)
    s2 = ThisDrawing.Utility.TranslateCoordinates(lnSpacing.EndPoint, acWorld, acUCS, False)
    
    If AlignUCS Then
        'UCS Alignment
        If Abs(w2(0) - w1(0)) <= Abs(w2(1) - w1(1)) Then
            'vertical web
            w1(0) = (w1(0) + w2(0)) / 2
            w2(0) = w1(0)
            s1(1) = (s1(1) + s2(1)) / 2
            s2(1) = s1(1)
            WebDir = Vertical
        Else
            'horizontal web
            w1(1) = (w1(1) + w2(1)) / 2
            w2(1) = w1(1)
            s1(0) = (s1(0) + s2(0)) / 2
            s2(0) = s1(0)
            WebDir = Horizontal
        End If
    Else
        'Web Alignment
        If w2(0) = w1(0) Then
            'vertical web
            s1(1) = (s1(1) + s2(1)) / 2
            s2(1) = s1(1)
            WebDir = Vertical
        Else
            If w2(1) = w1(1) Then
                'horizontal web
                s1(0) = (s1(0) + s2(0)) / 2
                s2(0) = s1(0)
                WebDir = Horizontal
            Else
                'the web is at an angle
                ks1 = (w2(1) - w1(1)) / (w2(0) - w1(0))
                ks2 = ks1
                If ks1 > 0 Then
                    kw = -Tan(pi / 2 - Atn(ks1))
                Else
                    kw = Tan(pi / 2 - Atn(Abs(ks1)))
                End If
                bw = w1(1) - kw * w1(0)
                bs1 = s1(1) - ks1 * s1(0)
                bs2 = s2(1) - ks2 * s2(0)
                'project s1 and s2 onto the web direction
                s1(0) = (bs1 - bw) / (kw - ks1)
                s1(1) = s1(0) * ks1 + bs1
                s2(0) = (bs2 - bw) / (kw - ks2)
                s2(1) = s2(0) * ks2 + bs2
                WebDir = Skewed
            End If
        End If
    End If
    
    'effective web depth and spacing
    wd = Sqr((w2(0) - w1(0)) ^ 2 + (w2(1) - w1(1)) ^ 2)
    sp = Sqr((s2(0) - s1(0)) ^ 2 + (s2(1) - s1(1)) ^ 2)
    
    'hole depth
    HD = wd * HD_WD
    
    'hole length
    HL = wd * HL_WD
    If HL > sp * HL_SP Then
        HL = sp * HL_SP
    End If
    
    'determine corner radius
    CR = HD * CR_HD
    If CR > HD / 2 Then
        CR = HD / 2
    End If
    If CR > HL / 2 Then
        CR = HL / 2
    End If
    
    'OCS (matches with UCS) coordinates relative to (0,0)
    'vertex 1
    pts(0) = -HL / 2 + CR
    pts(1) = -HD / 2
    pts(2) = 0
    
    'vertex 2
    pts(3) = -HL / 2
    pts(4) = -HD / 2 + CR
    pts(5) = 0
    
    'vertex 3
    pts(6) = -HL / 2
    pts(7) = HD / 2 - CR
    pts(8) = 0
    
    'vertex 4
    pts(9) = -HL / 2 + CR
    pts(10) = HD / 2
    pts(11) = 0
        
    'vertex 5
    pts(12) = HL / 2 - CR
    pts(13) = HD / 2
    pts(14) = 0
    
    'vertex 6
    pts(15) = HL / 2
    pts(16) = HD / 2 - CR
    pts(17) = 0
    
    'vertex 7
    pts(18) = HL / 2
    pts(19) = -HD / 2 + CR
    pts(20) = 0
    
    'vertex 8
    pts(21) = HL / 2 - CR
    pts(22) = -HD / 2
    pts(23) = 0
    
    'rotate hole to position
    Select Case WebDir
        Case Vertical
            ang = 0 'no rotation is needed
        Case Horizontal
            ang = pi / 2
        Case Skewed
            'rotate around (0, 0) to align the hole depth direction with the web direction
            ang = -Atn((w2(0) - w1(0)) / (w2(1) - w1(1)))
    End Select
    If ang <> 0 Then
        For i = 0 To 22 Step 3
            RotatePoints pts(i), pts(i + 1), ang
        Next i
    End If
    
    'move the hole to its final location in OCS
    Select Case WebDir
        Case Vertical
            dx = (s1(0) + s2(0)) / 2
            dy = (w1(1) + w2(1)) / 2
        Case Horizontal
            dx = (w1(0) + w2(0)) / 2
            dy = (s1(1) + s2(1)) / 2
        Case Skewed
            'intersection of two perpendicular lines passing through mid points of w1-w2 and s1-s2
            kw = (s2(1) - s1(1)) / (s2(0) - s1(0))
            bw = (w2(1) + w1(1)) / 2 - kw * (w2(0) + w1(0)) / 2
            ks1 = (w2(1) - w1(1)) / (w2(0) - w1(0))
            bs1 = (s2(1) + s1(1)) / 2 - ks1 * (s2(0) + s1(0)) / 2
            dx = (bs1 - bw) / (kw - ks1)
            dy = ks1 * dx + bs1
    End Select
        
    For i = 0 To 22 Step 3
        pts(i) = pts(i) + dx
        pts(i + 1) = pts(i + 1) + dy
    Next i
    
    Set pln = ThisDrawing.ModelSpace.AddPolyline(pts)
    pln.Closed = True
    
    'set correct elevation in OCS
    w1 = ThisDrawing.Utility.TranslateCoordinates(w1, acUCS, acOCS, False, lnWeb.Normal)
    pln.Elevation = w1(2)
    
    'round corners
    For i = 0 To 7 Step 2
        pln.SetBulge i, -0.414213562373095
    Next i
    
    On Error Resume Next
    pln.Layer = sLayerName
    On Error GoTo 0
    
    pln.Update
End Function

Private Function RotatePoints(ByRef x As Double, ByRef y As Double, ang As Double)
    Dim x0 As Double
    Dim y0 As Double
    
    x0 = x
    y0 = y
   
    x = x0 * Cos(ang) - y0 * Sin(ang)
    y = x0 * Sin(ang) + y0 * Cos(ang)
End Function

Attribute VB_Name = "AcToolsMDGeneral"
Option Explicit

Public Enum MDGeneralGuidType
    mdgen_view_guid
    mdgen_part_guid
End Enum

Public Enum MDPostProcessParamType
    mdpp_prop_type_sc
    mdpp_prop_type_acad
    mdpp_prop_type_md
End Enum

Public Enum MDPostProcessConditionType
    mdpp_cond_type_equals
    mdpp_cond_type_does_not_equal
    mdpp_cond_type_starts_with
    mdpp_cond_type_contains
    mdpp_cond_type_does_not_contain
    mdpp_cond_type_less_than
    mdpp_cond_type_greater_than
End Enum

Public Enum MDPostProcessTargetType
    mdpp_target_type_object
    mdpp_target_type_acad_property
End Enum

Public Enum MDPostProcessActionObject
    mdpp_act_obj_delete
    mdpp_act_obj_unmodify
End Enum

Public Enum MDPostProcessActionAcadProp
    mdpp_act_acad_prop_set_to
End Enum

Public Function GetMDViewGuidsFromSelectionSet(selSet As AcadSelectionSet) As Collection
    Dim obj As AcadEntity
    Dim n As Long
    Dim cViewGuids As Collection
    Dim sGuid As String
        
    Set cViewGuids = New Collection
    
    For n = 0 To selSet.Count - 1
        Set obj = selSet.Item(n)
        sGuid = GetMDGuid(obj, mdgen_view_guid)
        If sGuid <> Empty Then
            AddUniqueElementToCollection cViewGuids, sGuid, sGuid
        End If
    Next n
    
    Set GetMDViewGuidsFromSelectionSet = cViewGuids
End Function

Public Function GetMDGuid(obj As AcadEntity, guidType As MDGeneralGuidType) As String
    Dim xdataOut As Variant
    Dim xtypeOut As Variant

    GetMDGuid = Empty

    If obj Is Nothing Then
        Exit Function
    End If
    
    On Error GoTo errXData
    obj.GetXData "", xtypeOut, xdataOut
    On Error GoTo 0
                
    If TypeName(xtypeOut) = "Empty" Then
        Exit Function
    End If
    
    If UBound(xdataOut, 1) < 4 Then
        Exit Function
    End If
    
    If LCase(CStr(xdataOut(0))) <> "scprodmdoutput" Then
        Exit Function
    End If
    
    Select Case guidType
    Case mdgen_view_guid
        GetMDGuid = CStr(xdataOut(2))
    Case mdgen_part_guid
        GetMDGuid = CStr(xdataOut(3))
    End Select
    Exit Function

errXData:
    Exit Function
End Function

Public Function GetMDModified(obj As AcadEntity) As Boolean
    Dim xdataOut As Variant
    Dim xtypeOut As Variant

    GetMDModified = False

    If obj Is Nothing Then
        Exit Function
    End If
    
    obj.GetXData "", xtypeOut, xdataOut
                
    If TypeName(xtypeOut) = "Empty" Then
        Exit Function
    End If
    
    If UBound(xdataOut, 1) < 4 Then
        Exit Function
    End If
    
    If LCase(CStr(xdataOut(0))) <> "scprodmdoutput" Then
        Exit Function
    End If
    
    On Error Resume Next
    GetMDModified = CBool(xdataOut(4))
    On Error GoTo 0
End Function

Public Function MDUnmodify(obj As AcadEntity) As Boolean
        Dim xdataOut As Variant
    Dim xtypeOut As Variant

    MDUnmodify = False

    If obj Is Nothing Then
        Exit Function
    End If
    
    obj.GetXData "", xtypeOut, xdataOut
                
    If TypeName(xtypeOut) = "Empty" Then
        Exit Function
    End If
    
    If UBound(xdataOut, 1) < 4 Then
        Exit Function
    End If
    
    If LCase(CStr(xdataOut(0))) <> "scprodmdoutput" Then
        Exit Function
    End If
    
    xdataOut(4) = 0
    obj.SetXData xtypeOut, xdataOut
    
    MDUnmodify = True
End Function

Attribute VB_Name = "AcToolsMDGroupObjs"
Option Explicit

Public Sub CTMDGroupObjects()
    Dim selSet As AcadSelectionSet
    Dim objs() As AcadEntity
    Dim sResult As String
    Dim cTargetViews As Collection
    Dim cStructuredObjs As Collection
    Dim n As Integer
        
    Set selSet = ThisDrawing.PickfirstSelectionSet
    Set cTargetViews = New Collection
    
    PromptInCommandLine vbLf
    
    If selSet.Count > 0 Then
        Set cTargetViews = GetMDViewGuidsFromSelectionSet(selSet)
        If cTargetViews.Count = 0 Then
            PromptInCommandLine "None of the selected entities is associated with a MarineDrafting view..."
            selSet.Clear
        End If
    End If
        
    If selSet.Count = 0 Then
        ThisDrawing.Utility.InitializeUserInput 0, "All Select More"
        On Error GoTo errCancelOperation
        sResult = ThisDrawing.Utility.GetKeyword("Specify valid MarineDrafting geometry inside the 2D views [<All>/Select/More...]:")
        If sResult = "" Then sResult = "All"
        On Error GoTo 0
        
        Select Case sResult
            Case "All"
                If ThisDrawing.ModelSpace.Count > 0 Then
                    ReDim objs(0 To ThisDrawing.ModelSpace.Count - 1) As AcadEntity
                    For n = 0 To ThisDrawing.ModelSpace.Count - 1
                        Set objs(n) = ThisDrawing.ModelSpace.Item(n)
                    Next n
                    selSet.AddItems objs
                End If
            Case "Select"
                selSet.SelectOnScreen
            Case "More"
                ThisDrawing.Utility.InitializeUserInput 0, "Back Reset"
                On Error GoTo errCancelOperation
                sResult = ThisDrawing.Utility.GetKeyword("Additional operations [<Back>/Reset All Groups in Drawing]:")
                If sResult = "" Then sResult = "Back"
                On Error GoTo 0
                
                Select Case sResult
                    Case "Reset"
                        While ThisDrawing.Groups.Count > 0
                            ThisDrawing.Groups(0).Delete
                        Wend
                        ThisDrawing.Utility.Prompt "Reset completed." & vbLf
                End Select
                                
                CTMDGroupObjects
                Exit Sub
        End Select
    End If
    
    If cTargetViews.Count = 0 Then
        Set cTargetViews = GetMDViewGuidsFromSelectionSet(selSet)
    End If
    
    If cTargetViews.Count > 0 Then
        ThisDrawing.Utility.InitializeUserInput 0, "Layer Part"
        On Error GoTo errCancelOperation
        sResult = ThisDrawing.Utility.GetKeyword("Choose method for grouping geometry [<Layer>/Part]:")
        If sResult = "" Then sResult = "Layer"
        On Error GoTo 0
        
        'reset existing AutoCAD groups for target views
        ClearGroupsInViews cTargetViews
        
        'structure MarineDrafting geometry
        Set cStructuredObjs = StructureObjectsInViews(cTargetViews)
        
        'form new AutoCad groups
        Select Case sResult
        Case "Layer"
            FormAcadGroups cStructuredObjs, True
        Case "Part"
            FormAcadGroups cStructuredObjs, False
        End Select
    Else
        ThisDrawing.Utility.Prompt "Unable to find any MarineDrafting views from the selected objects. Please, ensure that you select valid MarineDrafting geometry inside the view." & vbLf
        ThisDrawing.Utility.Prompt "Operation failed." & vbLf
        Exit Sub
    End If
    
    ThisDrawing.Utility.Prompt "Operation completed successfully." & vbLf
    Exit Sub
    
errCancelOperation:
    ThisDrawing.Utility.Prompt "Operation cancelled." & vbLf
End Sub

Private Function FormAcadGroups(ByRef cSource As Collection, bIsByLayer As Boolean)
    Dim n As Long
    Dim k As Long
    Dim appendObjs() As AcadEntity
    Dim bIsCollection As Boolean
    Dim cLayers As Collection
    Dim cGeom As Collection
    Dim acEntity As AcadEntity
    
    For n = 1 To cSource.Count
        If TypeName(cSource(n)) = "Collection" Then
            FormAcadGroups cSource(n), bIsByLayer
            bIsCollection = True
        Else
            bIsCollection = False
            Exit For
        End If
    Next n
    
    If bIsCollection Then
        Exit Function
    End If
           
    If cSource.Count >= 3 Then
        If bIsByLayer Then
            Set cLayers = New Collection
            For n = 3 To cSource.Count
                Set acEntity = cSource(n)
                If Not CheckInCollection(cLayers, acEntity.Layer) Then
                    cLayers.Add New Collection, acEntity.Layer
                End If
                Set cGeom = cLayers(acEntity.Layer)
                
                cGeom.Add acEntity
            Next n
            For Each cGeom In cLayers
                ReDim appendObjs(0 To cGeom.Count - 1) As AcadEntity
                For n = 1 To cGeom.Count
                    Set appendObjs(n - 1) = cGeom(n)
                Next n
                
                AppendToGroup (appendObjs)
            Next cGeom
        Else
            ReDim appendObjs(0 To cSource.Count - 3) As AcadEntity
            For n = 3 To cSource.Count
                Set appendObjs(n - 3) = cSource(n)
            Next n
            
            AppendToGroup (appendObjs)
        End If
    End If
End Function

Private Function AppendToGroup(ByRef appendObjs As Variant)
    Dim g As AcadGroup
    
    Set g = ThisDrawing.Groups.Add(Replace(CreateGUID(), "-", ""))
    g.AppendItems appendObjs
End Function

Private Function ClearGroupsInViews(cTargetViews As Collection)
    Dim n As Long
    Dim k As Long
    Dim acEntity As AcadEntity
    Dim sViewGuid As String
    Dim sTargetViewGuid As String
    Dim bIsDeleteGroup As Boolean
    
    For n = 0 To ThisDrawing.Groups.Count - 1
        If n > ThisDrawing.Groups.Count - 1 Then
            Exit For
        End If
        
        bIsDeleteGroup = False
        For Each acEntity In ThisDrawing.Groups(n)
            sViewGuid = GetMDGuid(acEntity, mdgen_view_guid)
            If sViewGuid <> Empty Then
                For k = 1 To cTargetViews.Count
                    sTargetViewGuid = cTargetViews(k)
                    If sTargetViewGuid = sViewGuid Then
                        bIsDeleteGroup = True
                        Exit For
                    End If
                Next k
            End If
            If bIsDeleteGroup Then
                Exit For
            End If
        Next acEntity
        If bIsDeleteGroup Then
            ThisDrawing.Groups(n).Delete
            n = n - 1
        End If
    Next n
End Function

Private Function StructureObjectsInViews(cTargetViews As Collection) As Collection
    Dim cObj As Collection
    Dim acEntity As AcadEntity
    Dim n As Long
    Dim k As Long
    Dim sViewGuid As String
    Dim sPartGuid As String
    Dim cResult As Collection
    Dim cView As Collection
    Dim cPart As Collection
            
    Set cResult = New Collection
        
    For n = 0 To ThisDrawing.ModelSpace.Count - 1
        Set acEntity = ThisDrawing.ModelSpace.Item(n)
        
        sViewGuid = GetMDGuid(acEntity, mdgen_view_guid)
        If sViewGuid <> Empty Then
            For k = 1 To cTargetViews.Count
                If sViewGuid = cTargetViews(k) Then
                    Exit For
                End If
            Next k
            If k <= cTargetViews.Count Then
                sPartGuid = GetMDGuid(acEntity, mdgen_part_guid)
                If sPartGuid <> Empty Then
                    If Not CheckInCollection(cResult, sViewGuid) Then
                        cResult.Add New Collection, sViewGuid
                    End If
                    Set cView = cResult(sViewGuid)
                    
                    If CheckInCollection(cView, sPartGuid) Then
                        Set cPart = cView(sPartGuid)
                    Else
                        cView.Add New Collection, sPartGuid
                        Set cPart = cView(sPartGuid)
                        
                        cPart.Add sViewGuid
                        cPart.Add sPartGuid
                    End If
                    
                    cPart.Add acEntity
                End If
            End If
        End If
        
    Next n
    
    Set StructureObjectsInViews = cResult
End Function

Private Function CheckInCollection(ByRef c As Collection, key As String) As Boolean
    Dim val As Variant
    
    CheckInCollection = True
    
    On Error GoTo errElementNotFound
    Set val = c(key)
    On Error GoTo 0
    Exit Function
    
errElementNotFound:
    CheckInCollection = False
End Function

Attribute VB_Name = "AcToolsMDPostProcess"
Option Explicit

Private cTSVData As Collection
Private cTSVHeaders As Collection
Private cTargetViews As Collection
Private nPartGuidColumnIndex As Long
Private cPostProcessItems As Collection

Public Sub CTMDPostProcess()
    Dim uf As ufMDPostProcess
    Dim bIsCancel As Boolean
            
    'select views for post processing
    PromptInCommandLine vbLf
    Set cTargetViews = SelectMarineDraftingViews(bIsCancel)
    
    If bIsCancel Then
        PromptInCommandLine "Operation cancelled."
        Exit Sub
    End If
        
    'bring up the form with settings
    Set uf = New ufMDPostProcess
    uf.lblViewsCount.Caption = cTargetViews.Count
    uf.show
    
    If uf.bIsCancel Then
        Unload uf
        Exit Sub
    End If
    
    If cTargetViews.Count = 0 Then
        Unload uf
        Exit Sub
    End If
    
    Set cTSVHeaders = uf.cTSVHeaders
    Set cTSVData = ReadTSVData(uf.tbDataFilePath.Text, cTSVHeaders)
    Set cPostProcessItems = uf.cPostProcessItems
    nPartGuidColumnIndex = GetCollectionIndex(cTSVHeaders, uf.cboxGuid.Text)
          
    Unload uf
        
    If cTSVData Is Nothing Then
        WarningMsg "Unable to read the ShipConstructor data file."
        Exit Sub
    End If
    
    PostProcessViews
    ThisDrawing.SendCommand "regenall" & vbCr
    
    PromptInCommandLine "Operation complete."
End Sub

Private Function SelectMarineDraftingViews(ByRef bIsCancel As Boolean) As Collection
    Dim selSet As AcadSelectionSet
    Dim objs() As AcadEntity
    Dim sResult As String
    Dim cViews As Collection
    Dim n As Long
    Dim ufProg As ufProgress
        
    bIsCancel = False
            
    Set selSet = ThisDrawing.PickfirstSelectionSet
    Set cViews = New Collection
    Set SelectMarineDraftingViews = New Collection
    
    If selSet.Count > 0 Then
        Set cViews = GetMDViewGuidsFromSelectionSet(selSet)
        If cViews.Count = 0 Then
            PromptInCommandLine "None of the selected entities are associated with a MarineDrafting view..."
            selSet.Clear
        End If
    End If
        
    If selSet.Count = 0 Then
        ThisDrawing.Utility.InitializeUserInput 0, "Select Options"
        On Error GoTo errCancelOperation
        sResult = ThisDrawing.Utility.GetKeyword("Select valid MarineDrafting geometry inside target 2D views [<Select>/Options]:")
        If sResult = "" Then sResult = "Select"
        On Error GoTo 0
        
        Select Case sResult
            Case "Options"
                Exit Function
            Case "Select"
                selSet.SelectOnScreen
        End Select
    End If
    
    If cViews.Count = 0 Then
        Set cViews = GetMDViewGuidsFromSelectionSet(selSet)
    End If
    
    If cViews.Count = 0 Then
        PromptInCommandLine "Unable to identify MarineDrafting views from selected objects. Please, ensure that you select valid MarineDrafting geometry located inside a 2D view."
        bIsCancel = True
        Exit Function
    End If
    
    Set SelectMarineDraftingViews = cViews
    Exit Function
    
errCancelOperation:
    bIsCancel = True
End Function

Private Function PostProcessViews()
    Dim v As AcadEntity
    Dim ufProg As ufProgress
    Dim dCount As Double
    Dim dInitialCount As Double
    
    Set ufProg = New ufProgress
    ufProg.SetStage "Processing views..."
    ufProg.show vbModeless
    
    dCount = 0
    dInitialCount = ThisDrawing.ModelSpace.Count
    For Each v In ThisDrawing.ModelSpace
        dCount = dCount + 1
                
        ufProg.SetProgress dCount / dInitialCount
        If ufProg.bIsCancel Then
            Exit For
        End If
        
        If IsInTargetView(GetMDGuid(v, mdgen_view_guid)) Then
            PostProcessEntity v
        End If
    Next v
    ufProg.Hide
    Unload ufProg
End Function

Private Function PostProcessEntity(v As AcadEntity) As Boolean
    Dim cItem As Collection
    Dim cConditions As Collection
    Dim cActions As Collection
    
    For Each cItem In cPostProcessItems
        Set cConditions = cItem(3)
        Set cActions = cItem(4)
        If AreAllConditionsMet(v, cConditions) Then
            PerformActions v, cActions
            DoEvents
        End If
    Next cItem
End Function

Private Function AreAllConditionsMet(v As AcadEntity, cConditions As Collection)
    Dim guid As String
    Dim cCond As Collection
    Dim prop As Variant
    Dim s1 As String
    Dim s2 As String
    
    AreAllConditionsMet = False
    
    On Error GoTo errObjectErased
    If v.Layer = "SCMD Original" Then
        'do nothing
    End If
    On Error GoTo 0
    
    'get the object guid
    guid = GetMDGuid(v, mdgen_part_guid)
            
    For Each cCond In cConditions
        'retrieve the property to evaluate
        Select Case cCond(1)
        Case mdpp_prop_type_sc:
            If guid = Empty Then Exit Function
            prop = GetTSVData(guid, cCond(2))
            If prop = Empty Then
                PromptInCommandLine "Retrieve Property> " & guid & ": unable to locate data for """ & cCond(2) & """."
                Exit Function
            End If
        Case mdpp_prop_type_acad:
            Select Case LCase(Trim(cCond(2)))
            Case "object type"
                prop = TypeName(v)
            Case Else
                On Error GoTo errRetrieveProperty
                prop = CallByName(v, Trim(LCase(cCond(2))), VbGet)
                On Error GoTo 0
            End Select
        
        Case mdpp_prop_type_md:
            Select Case Trim(LCase(cCond(2)))
            Case "modified"
                prop = GetMDModified(v)
            End Select
        End Select
                        
        'evaluate the property
        On Error GoTo errEvaluateProperty
        Select Case cCond(3)
        Case mdpp_cond_type_equals
            Select Case LCase(TypeName(prop))
            Case "string"
                If Trim(LCase(prop)) <> Trim(LCase(cCond(4))) Then Exit Function
            Case Else
                If prop <> CType(cCond(4), TypeName(prop)) Then Exit Function
            End Select
            
        Case mdpp_cond_type_does_not_equal
            Select Case LCase(TypeName(prop))
            Case "string"
                If Trim(LCase(prop)) = Trim(LCase(cCond(4))) Then Exit Function
            Case Else
                If prop = CType(cCond(4), TypeName(prop)) Then Exit Function
            End Select
        
        Case mdpp_cond_type_starts_with
            s1 = Trim(LCase(CStr(prop)))
            s2 = Trim(LCase(cCond(4)))
            If Left(s1, Len(s2)) <> s2 Then Exit Function
        
        Case mdpp_cond_type_contains
            s1 = Trim(LCase(CStr(prop)))
            s2 = Trim(LCase(cCond(4)))
            If InStr(s1, s2) <= 0 Then Exit Function
        
        Case mdpp_cond_type_does_not_contain
            s1 = Trim(LCase(CStr(prop)))
            s2 = Trim(LCase(cCond(4)))
            If InStr(s1, s2) > 0 Then Exit Function
            
        Case mdpp_cond_type_less_than
            If LCase(prop) = "n/a" Then Exit Function
            If CDbl(prop) >= CDbl(cCond(4)) Then Exit Function
            
        Case mdpp_cond_type_greater_than
            If LCase(prop) = "n/a" Then Exit Function
            If CDbl(prop) <= CDbl(cCond(4)) Then Exit Function
        
        End Select
        On Error GoTo 0
    Next cCond
    
    AreAllConditionsMet = True
    Exit Function
    
errObjectErased:
    'do nothing
    Exit Function

errRetrieveProperty:
    If Err.Number > 0 Then
        If TypeName(v) <> "IAcadBlockReference" Then
            PromptInCommandLine "Retrieve Property> " & TypeName(v) & "." & cCond(2) & ": " & Err.Description
        End If
        Err.Clear
    End If
    Exit Function
        
errEvaluateProperty:
    If Err.Number > 0 Then
        If TypeName(v) <> "IAcadBlockReference" Then
            If prop = Empty Then
                prop = "<Empty>"
            End If
            PromptInCommandLine "Evaluate Property> " & cCond(2) & "=" & prop & " vs. """ & cCond(4) & """: " & Err.Description
        End If
        Err.Clear
    End If
End Function

Private Function PerformActions(v As AcadEntity, cActions As Collection)
    Dim cAct As Collection
    Dim vValue As Variant
    Dim guid As String
    Dim s As String
    
    guid = GetMDGuid(v, mdgen_part_guid)
    
    For Each cAct In cActions
        Select Case cAct(1)
        'object actions
        Case mdpp_target_type_object:
            Select Case cAct(3)
            Case mdpp_act_obj_delete:
                v.Delete
            Case mdpp_act_obj_unmodify:
                MDUnmodify v
            End Select
        
        'ACAD property actions
        Case mdpp_target_type_acad_property:
            'determine the value
            If cAct(4) Then
                If guid <> Empty Then
                    vValue = GetTSVData(guid, cAct(5))
                    vValue = vValue & cAct(6)
                Else
                    vValue = Empty
                End If
            Else
                vValue = cAct(6)
            End If
            
            If vValue <> Empty Then
                Select Case cAct(3)
                Case mdpp_act_acad_prop_set_to:
                    Select Case cAct(2)
                    Case "Layer":
                        If GetCollectionIndex(ThisDrawing.Layers, vValue) < 0 Then
                            ThisDrawing.Layers.Add vValue
                        End If
                        v.Layer = vValue
                    Case Else
                        On Error GoTo errActionOnAcadProp
                        CallByName v, Trim(LCase(cAct(2))), VbSet, vValue
                        On Error GoTo 0
                    End Select
                End Select
            End If
        End Select
    Next cAct
    
    Exit Function

errActionOnAcadProp:
    If Err.Number > 0 Then
        If TypeName(v) <> "IAcadBlockReference" Then PromptInCommandLine "Perform Action> " & TypeName(v) & "." & cAct(2) & " set to """ & vValue & """: " & Err.Description
        Err.Clear
    End If
    Resume Next
End Function

Private Function GetTSVData(guid, header) As Variant
    Dim c As Collection
    Dim gg As String
    Dim n As Long
        
    GetTSVData = Empty
    
    If guid = Empty Then Exit Function
    gg = LCase(Trim(guid))
    
    If nPartGuidColumnIndex < 0 Then Exit Function
    
    n = GetCollectionIndex(cTSVHeaders, header)
    If n < 0 Then Exit Function
            
    For Each c In cTSVData
        If LCase(Trim(c(nPartGuidColumnIndex))) = gg Then
            Exit For
        End If
    Next c
    If Not c Is Nothing Then
        GetTSVData = c(n)
    End If
End Function


Private Function IsInTargetView(sViewGuid) As Boolean
    Dim i As Integer
    
    If sViewGuid = "" Or sViewGuid = Empty Then
        IsInTargetView = False
        Exit Function
    End If
    
    For i = 1 To cTargetViews.Count
        If sViewGuid = cTargetViews(i) Then
            IsInTargetView = True
            Exit Function
        End If
    Next i
    
    IsInTargetView = False
End Function

Attribute VB_Name = "AcToolsRemoveEnvelopes"
Option Explicit

Public Sub CTRemoveEnvelopes()
    Dim cKeywords As Collection
    Dim uf As ufRemoveEnvelopes
    Dim s As String
    Dim v As Variant
    Dim l As Long
    
    Set uf = New ufRemoveEnvelopes
    uf.show
    If uf.bIsCancel Then
        Unload uf
        PromptInCommandLine "Operation cancelled."
        Exit Sub
    End If
    Set cKeywords = uf.cKeywords
    Unload uf
    
    s = ""
    For Each v In cKeywords
        s = s & v & ", "
    Next v
    
    s = Left(s, Len(s) - 2)
    If Not QuestionMsg("Delete all envelopes for layers containing: " & s & "?", "Remove Envelopes") Then
        PromptInCommandLine "Operation cancelled."
        Exit Sub
    End If
        
    l = RemoveEnvelopes(cKeywords)
    
    ThisDrawing.SendCommand "regenall" & vbCr
    PromptInCommandLine "Operation complete: " & l & " objects deleted."
End Sub


Private Function RemoveEnvelopes(cKeywords As Collection) As Long
    Dim blk As AcadBlock
    Dim obj As AcadEntity
    Dim bIsDelete As Boolean
    Dim sKey As Variant
    
    RemoveEnvelopes = 0
    
    For Each blk In ThisDrawing.Blocks
        If Left(blk.Name, 1) <> "*" Then
        For Each obj In blk
            bIsDelete = False
            For Each sKey In cKeywords
                If InStr(LCase(obj.Layer), LCase(sKey)) > 0 Then
                    bIsDelete = True
                    Exit For
                End If
            Next sKey
            If bIsDelete Then
                obj.Delete
                RemoveEnvelopes = RemoveEnvelopes + 1
            End If
        Next obj
        End If
    Next blk
End Function

Attribute VB_Name = "AcToolsSpaceBomb"
Option Explicit

Private sResultLayerName As String
Private dblManualStepSize As Double
Private bIsAutoStep As Boolean
Private ufProg As ufProgress

Public Sub CTSpaceBomb()
    Dim sldBlock As Acad3DSolid
    Dim uf As ufSpaceBombControlParams
    Dim cResults As Collection
    
    Set uf = New ufSpaceBombControlParams
    uf.show
    If uf.bIsCancel Then
        Unload uf
        Exit Sub
    Else
        sResultLayerName = uf.tbLayerName.Text
        On Error GoTo errStepSize
        dblManualStepSize = CDbl(uf.tbManualStep.Text)
        On Error GoTo 0
        bIsAutoStep = uf.checkAutoStep.Value
        Unload uf
    End If
    
    If Not Initialize() Then
        PromptInCommandLine "Error: Unable to initialize the command."
        Exit Sub
    End If
    
    Set sldBlock = CreateOuterSolid(ThisDrawing.Layers(sResultLayerName))
    If sldBlock Is Nothing Then
        Terminate
        Exit Sub
    End If
                
    Set cResults = BuildInnerVolumes(sldBlock)
    If cResults Is Nothing Then
        Terminate
        Exit Sub
    End If
    
    Terminate
    
    ReportResults cResults
    PromptInCommandLine "Operation complete."
    Exit Sub

errStepSize:
    WarningMsg "The manual step value is set incorrectly. The value will be reset to: 1."
    dblManualStepSize = 1
    Resume Next
End Sub

Private Function Initialize() As Boolean
    PromptInCommandLine "Begin operation."
    ResetLayer sResultLayerName
    Set ufProg = New ufProgress
    
    SetUndo False
    Initialize = True
End Function

Private Function ReportResults(cSldResults As Collection)
    Dim sld As Acad3DSolid
    Dim dblVolumeTotal As Double
    Dim i As Integer
    Dim v As Variant
    Dim uf As ufSpaceBombResults
    Dim s As String
    
    Set uf = New ufSpaceBombResults
    
    i = 0
    dblVolumeTotal = 0
    PromptInCommandLine "-----  Estimated Volumes  ------"
    For Each sld In cSldResults
        i = i + 1
        s = "" & Format(Round(sld.Volume, 3), "0,0.0") & " cu. units | Level: " & i
        PromptInCommandLine s
        uf.tbResults = uf.tbResults & s & vbNewLine
        dblVolumeTotal = dblVolumeTotal + sld.Volume
    Next sld
    s = Format(Round(dblVolumeTotal, 3), "0,0.0") & " cu. units | Total: x"
    PromptInCommandLine s
    uf.tbResults = uf.tbResults & "--------------------" & vbNewLine
    uf.tbResults = uf.tbResults & s
    PromptInCommandLine "-------------------------------"
    
    uf.show vbModal
    Unload uf
End Function

Private Function Terminate()
    If ufProg.Visible Then
        ufProg.bIsCancel = True
        ufProg.Hide
    End If
    Unload ufProg
    SetUndo True
End Function

Private Function CreateOuterSolid(lResult As AcadLayer) As Acad3DSolid
    Dim cDwgObjects As Collection
    Dim minDwgExtents(0 To 2) As Double
    Dim maxDwgExtents(0 To 2) As Double
    Dim sldBlock As Acad3DSolid
    Dim sldTemp As Acad3DSolid
    Dim ptBlockCenterPoint(0 To 2) As Double
    Dim i As Integer

    'get all solids in the drawing
    Set cDwgObjects = GetDrawingExtentsFromSolids(minDwgExtents, maxDwgExtents)
    If cDwgObjects.Count = 0 Then
        PromptInCommandLine "Error: The current drawing does not contain any solids."
        Exit Function
    End If
    
    ufProg.show vbModeless
    ufProg.SetStage "Subtracting solids..."
    
    'create an outer boundary that encloses all solids
    ptBlockCenterPoint(0) = (maxDwgExtents(0) + minDwgExtents(0)) / 2
    ptBlockCenterPoint(1) = (maxDwgExtents(1) + minDwgExtents(1)) / 2
    ptBlockCenterPoint(2) = (maxDwgExtents(2) + minDwgExtents(2)) / 2
    
    Set sldBlock = ThisDrawing.ModelSpace.AddBox(ptBlockCenterPoint, maxDwgExtents(0) - minDwgExtents(0) + 10, _
            maxDwgExtents(1) - minDwgExtents(1) + 10, _
            maxDwgExtents(2) - minDwgExtents(2) + 10)
        
    sldBlock.Visible = False
    sldBlock.Layer = lResult.Name
        
    'hollow out the outer solid
    On Error GoTo errSolidBoolean
    For i = 1 To cDwgObjects.Count
        Set sldTemp = cDwgObjects(i).Copy
        If sldTemp.Volume > 0 Then
            sldBlock.Boolean acSubtraction, sldTemp
        Else
            sldTemp.Delete
        End If
        
        ufProg.SetProgress i / cDwgObjects.Count
        If ufProg.bIsCancel Then
            sldBlock.Delete
            PromptInCommandLine "Operation aborted."
            Exit Function
        End If
    Next i
    On Error GoTo 0
    
    Set CreateOuterSolid = sldBlock
    Exit Function
    
errSolidBoolean:
    Set sldTemp = cDwgObjects(i).Copy
    sldTemp.Layer = sResultLayerName
    sldBlock.Delete
    PromptInCommandLine "Error: Unable to subtract a 3D solid. The problem solid was copied to the " & sResultLayerName & " layer."
End Function

Private Function BuildInnerVolumes(sldBlock As Acad3DSolid) As Collection
    Dim z As Double
    Dim dblStep As Double
    Dim r As AcadRegion
    Dim cRegions As Collection
    Dim minExt As Variant
    Dim maxExt As Variant
    Dim minExtRgn As Variant
    Dim maxExtRgn As Variant
    Dim vExplodedObjs As Variant
    Dim vObj As Variant
    Dim i As Integer
    Dim j As Integer
    Dim iMaxLevel As Integer
    Dim iPctComplete As Integer
    Dim iPctCompleteOld As Integer
    Dim cSldResults As Collection
    Dim cResultLayers As Collection
    Dim cLayer As Collection
    Dim dblLayerHeight As Double
    Dim nCurLayer As Integer
    Dim sldResult As Acad3DSolid
    Dim bIsFirst As Boolean
    
    Set cResultLayers = New Collection
    Set cSldResults = New Collection
    iPctComplete = -1
    iPctCompleteOld = 0
    iMaxLevel = 0
    
    sldBlock.GetBoundingBox minExt, maxExt
    
    If bIsAutoStep Then
        dblStep = (maxExt(2) - minExt(2)) / 100
        If dblStep = 0 Then dblStep = 1
        If dblStep > 25 Then dblStep = 25
    Else
        dblStep = dblManualStepSize
    End If
    dblLayerHeight = dblStep * 10
    
    ufProg.SetStage "Filling empty spaces... Step size: " & Round(dblStep, 2) & " units"
    ufProg.SetProgress 0
    
    For z = minExt(2) - 0.01 To maxExt(2) Step dblStep
        Set r = SectionSolidAtElevation(sldBlock, z)
                        
        If Not r Is Nothing Then
            'explode the region
            r.Layer = sResultLayerName
            vExplodedObjs = r.Explode()
            r.Delete
            
            'delete non regions from exploded objects
            Set cRegions = New Collection
            i = 0
            For Each vObj In vExplodedObjs
                i = i + 1
                If TypeName(vObj) = "IAcadRegion" Then
                    vObj.GetBoundingBox minExtRgn, maxExtRgn
                    If minExt(0) = minExtRgn(0) And minExt(1) = minExtRgn(1) And _
                        maxExt(0) = maxExtRgn(0) And maxExt(1) = maxExtRgn(1) Then
                        'delete outer most region
                        vObj.Delete
                    Else
                        cRegions.Add vObj
                    End If
                Else
                    vObj.Delete
                End If
            Next vObj
            
            'convert regions to solids
            If cRegions.Count > 0 Then
                ConvertRegionsToSolids cRegions, cSldResults, dblStep
            End If
        End If
        iPctComplete = CInt(100 * (z - minExt(2)) / (maxExt(2) - minExt(2)))
        If iPctComplete <> iPctCompleteOld Then
            ufProg.SetProgress CDbl(iPctComplete) / 100
            iPctCompleteOld = iPctComplete
            Update
            DoEvents
        End If
                  
        'group results in layers
        nCurLayer = (z - minExt(2)) / dblLayerHeight
        If nCurLayer > cResultLayers.Count Then
            If iMaxLevel < cSldResults.Count Then iMaxLevel = cSldResults.Count
            cResultLayers.Add cSldResults
            Set cSldResults = New Collection
        End If
        If ufProg.bIsCancel Then
            PromptInCommandLine "Filling interrupted."
            ufProg.bIsCancel = False
            ufProg.show vbModeless
            Exit For
        End If
    Next z
    
    If cSldResults.Count > 0 Then
        If iMaxLevel < cSldResults.Count Then iMaxLevel = cSldResults.Count
        cResultLayers.Add cSldResults
        Set cSldResults = New Collection
    End If
    
    'merge slices
    For i = 1 To iMaxLevel
        ufProg.SetStage "Merging slices... Level: " & i & "/" & iMaxLevel
        bIsFirst = True
        Set sldResult = Nothing
        j = 0
        For Each cLayer In cResultLayers
            j = j + 1
            If cLayer.Count >= i Then
                If bIsFirst Then
                    Set sldResult = cLayer(i)
                    bIsFirst = False
                Else
                    sldResult.Boolean acUnion, cLayer(i)
                End If
            End If
            If CDbl(j) / 10 = CInt(j / 10) Then
                ufProg.SetProgress CDbl(j) / cResultLayers.Count
                'Update
                DoEvents
            End If
            If ufProg.bIsCancel Then
                PromptInCommandLine "Operation aborted."
                sldBlock.Delete
                Exit Function
            End If
        Next cLayer
        If Not sldResult Is Nothing Then
            cSldResults.Add sldResult
        End If
    Next i
    
    
    sldBlock.Delete
    
    Set BuildInnerVolumes = cSldResults
End Function

Private Function ConvertRegionsToSolids(ByRef cRegions As Collection, ByRef cSldResults As Collection, dblStep As Double)
    Dim cSortedRegions As Collection
    Dim sldResult As Acad3DSolid
    Dim vObj As Variant
    Dim i As Integer
    
    Set cSortedRegions = SortRegions(cRegions)
    i = 0
    For Each cRegions In cSortedRegions
        i = i + 1
        For Each vObj In cRegions
            Set sldResult = ThisDrawing.ModelSpace.AddExtrudedSolid(vObj, dblStep, 0)
            sldResult.Layer = sResultLayerName
            
            If cSldResults.Count < i Then
                cSldResults.Add sldResult
            Else
                sldResult.Boolean acUnion, cSldResults(i)
                cSldResults.Remove (i)
                If i > cSldResults.Count Then
                    cSldResults.Add sldResult
                Else
                    cSldResults.Add sldResult, , i
                End If
            End If
                                
            vObj.Delete
        Next vObj
    Next cRegions
End Function

Private Function SortRegions(cRegions As Collection) As Collection
    Dim cSorted As Collection
    Dim cLevel As Collection
    
    Set cSorted = New Collection
    
    While cRegions.Count > 0
        Set cLevel = FindLevel(cRegions)
        cSorted.Add cLevel
    Wend
    
    Set SortRegions = cSorted
End Function

Private Function FindLevel(ByRef cRegions As Collection) As Collection
    Dim cSameLevel As Collection
    Dim cNextLevel As Collection
    Dim i As Integer
    
    Set cSameLevel = New Collection
    Set cNextLevel = New Collection
    If cRegions.Count > 0 Then
        Do
            i = GetIndexOfLargestRegion(cRegions)
            If IsNestedRegion(cRegions(i), cSameLevel) Then
               cNextLevel.Add cRegions(i)
               cRegions.Remove i
            Else
                cSameLevel.Add cRegions(i)
                cRegions.Remove i
            End If
        Loop While cRegions.Count > 0
    End If
    
    Set cRegions = cNextLevel
    Set FindLevel = cSameLevel
End Function

Private Function GetIndexOfLargestRegion(cRegions As Collection) As Integer
    Dim minExt As Variant
    Dim maxExt As Variant
    Dim mminExt As Variant
    Dim mmaxExt As Variant
    Dim i As Integer
    Dim i0 As Integer
    Dim r As AcadRegion
    Dim bIsUpdate As Boolean
    
    i0 = -1
    For i = 1 To cRegions.Count
        Set r = cRegions(i)
        r.GetBoundingBox minExt, maxExt
        If i = 1 Then
            bIsUpdate = True
        Else
            If (mmaxExt(0) - mminExt(0)) * (mmaxExt(1) - mminExt(1)) < (maxExt(0) - minExt(0)) * (maxExt(1) - minExt(1)) Then
                bIsUpdate = True
            Else
                bIsUpdate = False
            End If
        End If
        
        If bIsUpdate Then
            mminExt = minExt
            mmaxExt = maxExt
            i0 = i
        End If
    Next i
    
    GetIndexOfLargestRegion = i0
End Function

Private Function IsNestedRegion(rTest As AcadRegion, cRegions As Collection) As Boolean
    Dim r As AcadRegion
    Dim minExt As Variant
    Dim maxExt As Variant
    Dim mminExt As Variant
    Dim mmaxExt As Variant
    
    rTest.GetBoundingBox mminExt, mmaxExt
    
    For Each r In cRegions
        r.GetBoundingBox minExt, maxExt
        If mminExt(0) >= minExt(0) And mminExt(1) >= minExt(1) And _
            mmaxExt(0) <= maxExt(0) And mmaxExt(1) <= maxExt(1) Then
            IsNestedRegion = True
            Exit Function
        End If
    Next r
    IsNestedRegion = False
End Function

Private Function SectionSolidAtElevation(sld As Acad3DSolid, z As Double) As AcadRegion
    Dim sectionPt1(0 To 2) As Double
    Dim sectionPt2(0 To 2) As Double
    Dim sectionPt3(0 To 2) As Double
    
    sectionPt1(0) = 0: sectionPt1(1) = 0: sectionPt1(2) = z
    sectionPt2(0) = 1: sectionPt2(1) = 0: sectionPt2(2) = z
    sectionPt3(0) = 0: sectionPt3(1) = 1: sectionPt3(2) = z
    
    Set SectionSolidAtElevation = sld.SectionSolid(sectionPt1, sectionPt2, sectionPt3)
End Function

Attribute VB_Name = "AcToolsUCS"
Option Explicit

Public Sub CTImportUCSList()
    Dim srcPath As String
    Dim srcDoc As AcadDocument
    Dim destDoc As AcadDocument
    Dim ucsNew As AcadUCS
    Dim ucsTemp As AcadUCS
    Dim UCS As AcadUCS
    Dim Origin(0 To 2) As Double
    Dim xAxisPnt(0 To 2) As Double
    Dim yAxisPnt(0 To 2) As Double
            
    srcPath = FileBrowseOpen("", "", "*.dwg|*.dwg", 0)
    If srcPath = "" Then
        Exit Sub
    End If
    
    Set destDoc = ActiveDocument
    Set srcDoc = Documents.Open(srcPath, True)
                
    Origin(0) = 4: Origin(1) = 5: Origin(2) = 3
    xAxisPnt(0) = 5: xAxisPnt(1) = 5: xAxisPnt(2) = 3
    yAxisPnt(0) = 4: yAxisPnt(1) = 6: yAxisPnt(2) = 3
    
    For Each UCS In srcDoc.UserCoordinateSystems
        If UCSExists(UCS.Name, destDoc) Then
            destDoc.Utility.Prompt "The UCS already exists in the current drawing: " & UCS.Name & vbLf
        Else
            Set ucsNew = destDoc.UserCoordinateSystems.Add(Origin, xAxisPnt, yAxisPnt, UCS.Name)
            ucsNew.Origin = UCS.Origin
            ucsNew.XVector = UCS.XVector
            ucsNew.YVector = UCS.YVector
            destDoc.Utility.Prompt "Imported UCS: " & UCS.Name & vbLf
        End If
        
    Next UCS
    
    srcDoc.Close
End Sub

Public Sub CTRenameUCSList()
    Dim sTextToReplace As String
    Dim sTextNew As String
    Dim sNewName As String
    Dim sOldName As String
    Dim ucsTemp As AcadUCS
    Dim bIsRenameFail As Boolean
    Dim bIsFound As Boolean
    Dim sResult As String
        
    On Error GoTo errCancelRename
    
    ThisDrawing.Utility.InitializeUserInput 128, "LIST"
    
    Do
        sTextToReplace = ThisDrawing.Utility.GetString(1, "Enter the character sequence to be replaced in the UCSs names: [LIST all UCSs in the drawing]")
        If sTextToReplace = "LIST" Then ListUCSs
    Loop While sTextToReplace = "LIST"
    
    'sTextToReplace = ThisDrawing.Utility.GetString(1, "Enter the character sequence to be replaced in the UCSs names: ")
    sTextNew = ThisDrawing.Utility.GetString(1, "Enter the new character sequence to replace with: ")
    On Error GoTo 0
    
    bIsFound = False
    For Each ucsTemp In ThisDrawing.UserCoordinateSystems
        If InStr(1, ucsTemp.Name, sTextToReplace, vbTextCompare) > 0 Then
            bIsFound = True
            sNewName = Replace(ucsTemp.Name, sTextToReplace, sTextNew, , , vbTextCompare)
            
            If sNewName <> ucsTemp.Name Then
                If UCSExists(sNewName) Then
                    ThisDrawing.Utility.Prompt "The UCS name already exists: " & sNewName & ". Unable to rename: " & ucsTemp.Name & "." & vbLf
                Else
                    sOldName = ucsTemp.Name
                    bIsRenameFail = False
                    
                    On Error GoTo errRenameFail
                    ucsTemp.Name = sNewName
                    On Error GoTo 0
                    If Not bIsRenameFail Then
                        ThisDrawing.Utility.Prompt (sOldName) & " was renamed to: " & sNewName & vbLf
                    End If
                End If
            Else
                ThisDrawing.Utility.Prompt "The new name for the UCS already matches its current one: " & sNewName & vbLf
            End If
        End If
    Next ucsTemp
    
    If Not bIsFound Then
        ThisDrawing.Utility.Prompt "Unable to find a single UCS containing """ & sTextToReplace & """ in its name." & vbLf
    End If
    
    Exit Sub

errCancelRename:
    Exit Sub
    
errRenameFail:
    ThisDrawing.Utility.Prompt Err.Description & vbNewLine
    bIsRenameFail = True
    Resume Next
    Exit Sub

errCancelReviewUCSList:
    Exit Sub
End Sub

Private Function ListUCSs()
    Dim ucsTemp As AcadUCS

    ThisDrawing.Utility.Prompt vbLf & "The current drawing contains the following UCSs:" & vbLf
    For Each ucsTemp In ThisDrawing.UserCoordinateSystems
        ThisDrawing.Utility.Prompt ucsTemp.Name & vbLf
    Next ucsTemp
End Function

Private Function UCSExists(sUCSName As String, Optional dwg As AcadDocument = Nothing) As Boolean
    Dim ucsTemp As AcadUCS
    
    If dwg Is Nothing Then
        Set dwg = ThisDrawing
    End If
    
    
    For Each ucsTemp In dwg.UserCoordinateSystems
        If ucsTemp.Name = sUCSName Then
            UCSExists = True
            Exit Function
        End If
    Next ucsTemp
    
    UCSExists = False
End Function

Attribute VB_Name = "GenCollection"
Option Explicit

Public Function GetCollectionIndex(cCollection As Variant, vSearchValue As Variant) As Long
    Dim v As Variant
    Dim vSource As Variant
    Dim i As Integer
    
    GetCollectionIndex = -1
    
    If TypeName(vSearchValue) = "String" Then
        vSearchValue = LCase(Trim(vSearchValue))
    End If
    
    i = 0
    For Each v In cCollection
        i = i + 1
        Select Case LCase(TypeName(v))
        Case "string"
            vSource = LCase(Trim(v))
        Case "iacadlayer"
            vSource = v.Name
        Case Else
            vSource = v
        End Select
        If vSource = vSearchValue Then
            GetCollectionIndex = i
            Exit Function
        End If
    Next v
End Function

Public Function AddUniqueElementToCollection(ByRef c As Collection, val As Variant, Optional key As String = Empty) As Boolean
    Dim n As Long
    Dim v As Variant
            
    AddUniqueElementToCollection = True
                
    If key <> Empty Then
        'if the key is provided, attempt to access a collection item by key
        On Error GoTo errKeyNotFound
        v = c(key)
        On Error GoTo 0
        
        'if the key is confirmed, do not add a new elemen to the collection
        AddUniqueElementToCollection = False
        Exit Function
    End If
    
    'if the key is not provided, consider values to be unique elements
    For n = 0 To c.Count
        If val = c(n) Then
            'if the value already presents, set the flag to skip adding it to the collection
            AddUniqueElementToCollection = False
            Exit For
        End If
    Next n
    
    If AddUniqueElementToCollection Then
        'add the value to the collection if the value is unique
        c.Add val
    End If
    
    Exit Function

errKeyNotFound:
    c.Add val, key
End Function

Public Function CloneCollectionItem(vItem As Variant) As Variant
    Dim v As Variant
    Dim cRes As Variant
    
    If TypeName(vItem) = "Collection" Then
        Set cRes = New Collection
        For Each v In vItem
            cRes.Add CloneCollectionItem(v)
        Next v
        Set CloneCollectionItem = cRes
    Else
        CloneCollectionItem = vItem
    End If
End Function

Attribute VB_Name = "GenDrawing"
Option Explicit

Public Function SetUndo(bIsEnabled As Boolean)
    Dim var As Double
    
    var = ThisDrawing.GetVariable("UNDOCTL")
    
    If bIsEnabled Then
        If Not (var And 1) Then
            ThisDrawing.SendCommand "UNDO" & vbCr & "A" & vbCr
        End If
        ThisDrawing.SendCommand "UNDO" & vbCr & "A" & vbCr & "ON" & vbCr
    Else
        If CInt(var / 2) <> var / 2 Then
            ThisDrawing.SendCommand "UNDO" & vbCr & "C" & vbCr & "None" & vbCr
        End If
    End If
    
    ThisDrawing.Utility.Prompt vbLf
    DoEvents
End Function

Public Function PromptInCommandLine(sText As String)
    If Not ThisDrawing Is Nothing Then
        ThisDrawing.Utility.Prompt (sText & vbLf)
        DoEvents
    End If
End Function

Public Function ResetLayer(sLayerName As String) As AcadLayer
    Dim bIsFound As Boolean
    Dim l As AcadLayer
    Dim vObj As AcadEntity
        
    bIsFound = False
    For Each l In ThisDrawing.Layers
        If l.Name = sLayerName Then
            bIsFound = True
            Exit For
        End If
    Next l
    
    If Not bIsFound Then
        Set l = ThisDrawing.Layers.Add(sLayerName)
    Else
        l.Lock = False
        For Each vObj In ThisDrawing.ModelSpace
            If vObj.Layer = l.Name Then
                vObj.Delete
            End If
        Next vObj
    End If
    
    Set ResetLayer = l
    Update
End Function

Public Function DrawBox(box As Variant) As Acad3DSolid
    Dim c(0 To 2) As Double
    Dim dx As Double
    Dim dy As Double
    Dim dz As Double
        
    c(0) = box(0): c(1) = box(1): c(2) = box(2)
    If UBound(box) = 3 Then
        dx = box(3): dy = box(3): dz = box(3)
    Else
        dx = box(3): dy = box(4): dz = box(5)
    End If
    Set DrawBox = ThisDrawing.ModelSpace.AddBox(c, dx, dy, dz)
    Update
End Function

Public Function DrawBoxes(cBoxes As Collection)
    Dim box As Variant
    For Each box In cBoxes
        DrawBox box
    Next box
    Update
End Function

Public Function GetDrawingExtentsFromSolids(ByRef minDwgExtents() As Double, ByRef maxDwgExtents() As Double) As Collection
    Dim obj As Variant
    Dim objMin As Variant
    Dim objMax As Variant
    Dim i As Integer
    Dim bIsFirstSolid As Boolean
    
    bIsFirstSolid = True
    For i = 0 To 2
        minDwgExtents(i) = 0: maxDwgExtents(i) = 0
    Next i
    
    If ThisDrawing Is Nothing Then
        Set GetDrawingExtentsFromSolids = Nothing
        Exit Function
    End If
    
    Set GetDrawingExtentsFromSolids = New Collection
    
    For Each obj In ThisDrawing.ModelSpace
        If TypeName(obj) = "IAcad3DSolid" Then
            obj.GetBoundingBox objMin, objMax
            GetDrawingExtentsFromSolids.Add obj
            For i = 0 To 2
                If bIsFirstSolid Then
                    minDwgExtents(i) = objMin(i)
                    maxDwgExtents(i) = objMax(i)
                Else
                    If objMin(i) < minDwgExtents(i) Then
                        minDwgExtents(i) = objMin(i)
                    End If
                    If objMax(i) > maxDwgExtents(i) Then
                        maxDwgExtents(i) = objMax(i)
                    End If
                End If
            Next i
            bIsFirstSolid = False
        End If
    Next obj
End Function

Public Function WarningMsg(sMessageText As String)
    MsgBox sMessageText, vbExclamation, "Warning"
End Function

Public Function CriticalMsg(sCallerName As String, sMessageText As String)
    MsgBox sCallerName & ": " & sMessageText, vbCritical, "Error"
End Function

Public Function QuestionMsg(sMessageText As String, Optional sTitle As String = "Attention") As Boolean
    If MsgBox(sMessageText, vbYesNoCancel + vbQuestion, sTitle) = vbYes Then
        QuestionMsg = True
    Else
        QuestionMsg = False
    End If
End Function

Attribute VB_Name = "GenFileSystem"
Option Explicit

'----------------------------------------------------------------------
' 64 bit VBA 7 version of File and Folder Browswers
' FileBrowseOpen()
' FileBrowseSave()
' FolderBrowse()
' Much of the original 32 bit module was donated by the good people of XtremeVbTalk.com
' I massaged it to be 64 bit with VBA 7 code lifted from numerous sites on the web
'----------------------------------------------------------------------

Private Declare PtrSafe Function GetOpenFileName Lib "comdlg32.dll" Alias _
    "GetOpenFileNameA" (pOpenfilename As OPENFILENAME) As Long

Private Declare PtrSafe Function GetSaveFileName Lib "comdlg32.dll" Alias _
    "GetSaveFileNameA" (pOpenfilename As OPENFILENAME) As Long

Private Declare PtrSafe Function SHBrowseForFolder Lib "shell32.dll" _
    Alias "SHBrowseForFolderA" (lpBrowseInfo As BrowseInfo) As Long

Private Declare PtrSafe Function SHGetPathFromIDList Lib "shell32.dll" _
    (ByVal pidList As LongPtr, ByVal lpBuffer As String) As Long

Public Declare PtrSafe Function SendMessageA Lib "user32" _
    (ByVal hwnd As LongPtr, ByVal wMsg As Long, ByVal wParam As LongPtr, lParam As Any) As LongPtr

Private Declare PtrSafe Sub CoTaskMemFree Lib "ole32.dll" (ByVal hMem As LongPtr)

Private Const BIF_RETURNONLYFSDIRS As Long = 1
Private Const CSIDL_DRIVES As Long = &H11
Private Const WM_USER As Long = &H400
Private Const MAX_PATH As Long = 260
'// message from browser
Private Const BFFM_INITIALIZED As Long = 1
Private Const BFFM_SELCHANGED As Long = 2
Private Const BFFM_VALIDATEFAILEDA As Long = 3 '// lParam:szPath ret:1(cont),0(EndDialog)
Private Const BFFM_VALIDATEFAILEDW As Long = 4 '// lParam:wzPath ret:1(cont),0(EndDialog)
Private Const BFFM_IUNKNOWN As Long = 5 '// provides IUnknown to client. lParam: IUnknown*
'// messages to browser
Private Const BFFM_SETSTATUSTEXTA As Long = WM_USER + 100
Private Const BFFM_ENABLEOK As Long = WM_USER + 101
Private Const BFFM_SETSELECTIONA As Long = WM_USER + 102
Private Const BFFM_SETSELECTIONW As Long = WM_USER + 103
Private Const BFFM_SETSTATUSTEXTW As Long = WM_USER + 104
Private Const BFFM_SETOKTEXT As Long = WM_USER + 105 '// Unicode only
Private Const BFFM_SETEXPANDED As Long = WM_USER + 106 '// Unicode only


Private Type OPENFILENAME
    lStructSize As Long
    hWndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As LongPtr
    lpTemplateName As String
    End Type
    Public Type BrowseInfo
    hWndOwner As LongPtr
    pIDLRoot As LongPtr
    pszDisplayName As String
    lpszTitle As String
    ulFlags As Long
    lpfnCallback As LongPtr
    lParam As LongPtr
    iImage As Long
End Type
 


#If Win64 Then
    Private Declare PtrSafe Function GetParent Lib "user32.dll" (ByVal hwnd As LongPtr) As LongPtr
#Else
    Private Declare Function GetParent Lib "user32.dll" (ByVal hwnd As Long) As Long
#End If
 
#If Win64 Then
    Public Function GetUserformHwnd( _
        ByRef ufmTarget As MSForms.UserForm) As LongPtr
     
    Dim lngHwndControl As LongPtr
         
#Else
    Public Function GetUserformHwnd( _
        ByRef ufmTarget As MSForms.UserForm) As Long
     
    Dim lngHwndControl As Long
     
#End If
 
    Dim objControl As MSForms.Control
    Dim strRandomName As String
     
    Randomize
    strRandomName = CStr(Rnd)
     
    Set objControl = ufmTarget.Controls.Add( _
        "Forms.Frame.1", strRandomName, False)
     
    objControl.Left = ufmTarget.ScrollLeft + ufmTarget.InsideWidth
    objControl.Visible = True
    lngHwndControl = objControl.[_GethWnd]
     
    GetUserformHwnd = GetParent(GetParent(lngHwndControl))
    ufmTarget.Controls.Remove strRandomName
End Function


'====== File Browsers for 64 bit VBA 7 ========
Public Function FileBrowseOpen(ByVal sInitFolder As String, _
        ByVal sTitle As String, _
        ByVal sFilter As String, _
        ByVal nFilterIndex As Integer, _
        Optional hwnd As LongPtr = 0) As String

    Dim OpenFile As OPENFILENAME
    Dim lReturn As Long
    
    sInitFolder = CorrectPath(sInitFolder)
        
    OpenFile.lpstrInitialDir = sInitFolder
    
    ' Swap filter separator for api separator
     sFilter = Replace(sFilter, "|", Chr(0))
    
    OpenFile.lpstrFilter = sFilter
    OpenFile.nFilterIndex = nFilterIndex
    OpenFile.lpstrTitle = sTitle
        
    OpenFile.hWndOwner = hwnd
    OpenFile.lpstrFile = String(257, 0)
    OpenFile.nMaxFile = LenB(OpenFile.lpstrFile) - 1
    OpenFile.lStructSize = LenB(OpenFile)
    
    OpenFile.lpstrFileTitle = OpenFile.lpstrFile
    OpenFile.nMaxFileTitle = OpenFile.nMaxFile
    
    OpenFile.flags = 0
    
    lReturn = GetOpenFileName(OpenFile)
    
    If lReturn = 0 Then
        FileBrowseOpen = ""
    Else
        FileBrowseOpen = Trim(Left(OpenFile.lpstrFile, InStr(1, OpenFile.lpstrFile, vbNullChar) - 1))
    End If
End Function
Public Function FileBrowseSave(ByVal sDefaultFilename As String, _
        ByVal sInitFolder As String, _
        ByVal sTitle As String, _
        ByVal sFilter As String, _
        ByVal nFilterIndex As Integer, _
        Optional hwnd As LongPtr = 0, _
        Optional sEnsureExtension As String = "") As String
    
    Dim PadCount As Integer
    Dim OpenFile As OPENFILENAME
    Dim lReturn As Long
    Dim s As String
    
    sInitFolder = CorrectPath(sInitFolder)
    
    ' Swap filter separator for api separator
    sFilter = Replace(sFilter, "|", Chr(0))
    
    OpenFile.lpstrFilter = sFilter
    OpenFile.nFilterIndex = 1
    OpenFile.hWndOwner = hwnd
    
    PadCount = 260 - Len(sDefaultFilename)
    OpenFile.lpstrFile = sDefaultFilename & String(PadCount, Chr(0))
    'OpenFile.lpstrFile = String(257, 0)
    OpenFile.nMaxFile = LenB(OpenFile.lpstrFile) - 1
    OpenFile.lStructSize = LenB(OpenFile)
    
    OpenFile.lpstrFileTitle = OpenFile.lpstrFile
    OpenFile.nMaxFileTitle = OpenFile.nMaxFile
    OpenFile.lpstrInitialDir = sInitFolder
    OpenFile.lpstrTitle = sTitle
    OpenFile.flags = 0
    lReturn = GetSaveFileName(OpenFile)
        
    If lReturn = 0 Then
        FileBrowseSave = ""
    Else
        s = Trim(Left(OpenFile.lpstrFile, InStr(1, OpenFile.lpstrFile, vbNullChar) - 1))
        If sEnsureExtension <> "" Then
            If LCase(Right(s, Len(sEnsureExtension))) <> (LCase(sEnsureExtension)) Then
                If Left(sEnsureExtension, 1) = "." Then
                    s = s & sEnsureExtension
                Else
                    s = s & "." & sEnsureExtension
                End If
            End If
        End If
        FileBrowseSave = s
    End If
End Function
 

'====== Folder Browser for 64 bit VBA 7 ========
Public Function FolderBrowse(ByVal sDialogTitle As String, ByVal sInitFolder As String) As String
    Dim ReturnPath As String
    
    Dim b(MAX_PATH) As Byte
    Dim pItem As Long
    Dim sFullPath As String
    Dim bi As BrowseInfo
    Dim ppidl As Long
    
    sInitFolder = CorrectPath(sInitFolder)
    
    ' Note VBA windows and dialogs do not have an hWnd property.
    bi.hWndOwner = 0 'Windows Main Screen handle.
    
    ' SHGetSpecialFolderLocation bi.hWndOwner, CSIDL_DRIVES, ppidl
    
    bi.pIDLRoot = 0 'ppidl
    bi.pszDisplayName = VarPtr(b(0))
    bi.lpszTitle = sDialogTitle
    bi.ulFlags = BIF_RETURNONLYFSDIRS
    If FolderExists(sInitFolder) Then bi.lpfnCallback = PtrToFunction(AddressOf BFFCallback)
    bi.lParam = StrPtr(sInitFolder)
    pItem = SHBrowseForFolder(bi)
    
    If pItem Then ' Succeeded
        sFullPath = Space$(MAX_PATH)
        If SHGetPathFromIDList(pItem, sFullPath) Then
            ReturnPath = Left$(sFullPath, InStr(sFullPath, vbNullChar) - 1) ' Strip nulls
            CoTaskMemFree pItem
        End If
    End If
    
    If ReturnPath <> "" Then
        If Right$(ReturnPath, 1) <> "\" Then
            ReturnPath = ReturnPath & "\"
        End If
    End If
    
    FolderBrowse = ReturnPath
End Function

'typedef int (CALLBACK* BFFCALLBACK)(HWND hwnd, UINT uMsg, LPARAM lParam, LPARAM lpData);
Private Function BFFCallback(ByVal hwnd As LongPtr, ByVal uMsg As LongPtr, ByVal lParam As LongPtr, ByVal sData As String) As LongPtr
    If uMsg = BFFM_INITIALIZED Then
        SendMessageA hwnd, BFFM_SETSELECTIONA, True, ByVal sData
    End If
End Function

Private Function PtrToFunction(ByVal lFcnPtr As LongPtr) As LongPtr
    PtrToFunction = lFcnPtr
End Function

Private Function CorrectPath(ByVal sPath As String) As String
    If Right$(sPath, 1) = "\" Then
        If Len(sPath) > 3 Then sPath = Left$(sPath, Len(sPath) - 1) ' Strip backslash from non-root
    Else
        If Len(sPath) = 2 Then sPath = sPath & "\" ' Append backslash to root
    End If
    CorrectPath = sPath
End Function

Public Function FolderExists(ByVal sFolderName As String) As Boolean
    Dim att As Long
    
    On Error Resume Next
    att = GetAttr(sFolderName)
    If Err.Number = 0 Then
        FolderExists = True
    Else
        Err.Clear
        FolderExists = False
    End If
    On Error GoTo 0
End Function

Public Function FileExists(sFilePath As String) As Boolean
    Dim TestStr As String
    
    If Trim(sFilePath) = "" Then
        FileExists = False
        Exit Function
    End If
        
    TestStr = ""
    On Error Resume Next
    TestStr = Dir(sFilePath)
    On Error GoTo 0
    If TestStr = "" Then
        FileExists = False
    Else
        FileExists = True
    End If
End Function

Public Function GetFolderPath(sFilePath As String) As String
    Dim i As Long
    
    GetFolderPath = ""
    sFilePath = Trim(sFilePath)
    If sFilePath = "" Then
        Exit Function
    End If
    
    For i = Len(sFilePath) To 1 Step -1
        Select Case Mid(sFilePath, i, 1)
            Case "\", "/"
                Exit For
        End Select
    Next i
    If i > 1 Then
        GetFolderPath = Left(sFilePath, i - 1)
    End If
End Function

Public Function ReadTSVHeaders(sFilePath As String) As Collection
    Dim s As String
    
    If Not FileExists(sFilePath) Then
        Set ReadTSVHeaders = Nothing
        Exit Function
    End If
    
    Open sFilePath For Input Access Read As #1
    If Not EOF(1) Then
        Line Input #1, s
        Close #1
        If s <> "" Then
            Set ReadTSVHeaders = ParseTSVString(s)
        Else
            Set ReadTSVHeaders = Nothing
        End If
    Else
        Set ReadTSVHeaders = Nothing
    End If
End Function

Public Function ReadTSVData(sFilePath As String, cHeaders As Collection) As Collection
    Dim s As String
    Dim cData As Collection
    Dim cResult As Collection
    
    If Not FileExists(sFilePath) Then
        Set ReadTSVData = Nothing
        Exit Function
    End If
    
    If cHeaders.Count < 2 Then
        Set ReadTSVData = Nothing
        Exit Function
    End If
    
    Open sFilePath For Input Access Read As #1
    If Not EOF(1) Then Line Input #1, s 'skip over headers
        
    While Not EOF(1)
        Line Input #1, s
        If s <> "" Then
            Set cData = ParseTSVString(s)
            If cData.Count = cHeaders.Count Then
                If cResult Is Nothing Then
                    Set cResult = New Collection
                End If
                cResult.Add cData
            Else
                Set ReadTSVData = Nothing
                Close #1
                Exit Function
            End If
        End If
    Wend
    Close #1
    
    Set ReadTSVData = cResult
End Function

Private Function ParseTSVString(sTSV As String) As Collection
    Dim i As Integer
    Dim cResult As Collection
    Dim s As String
    Dim c As String
    Dim bIsQuote As Boolean
    
    Set cResult = New Collection
    s = ""
    bIsQuote = False
    For i = 1 To Len(sTSV)
        c = Mid(sTSV, i, 1)
        Select Case c
        Case Chr(9):
            If bIsQuote Then
                s = s & c
            Else
                cResult.Add s
                s = ""
            End If
        Case """":
            bIsQuote = Not bIsQuote
        Case Else
            s = s & c
        End Select
    Next i
        
    If s <> "" Then
        cResult.Add s
    End If
         
    If cResult.Count > 0 Then
        Set ParseTSVString = cResult
    Else
        Set ParseTSVString = Nothing
    End If
End Function

Attribute VB_Name = "GenMisc"
Option Explicit

Public Const pi As Double = 3.14159265358979

Public Function CreateGUID() As String
    CreateGUID = Mid$(CreateObject("Scriptlet.TypeLib").guid, 2, 36)
End Function

Public Function CType(v As Variant, sTypeName As String) As Variant
    Select Case LCase(sTypeName)
    Case "boolean"
        CType = CBool(v)
    Case "byte"
        CType = CByte(v)
    Case "double"
        CType = CDbl(v)
    Case "integer"
        CType = CInt(v)
    Case "long"
        CType = CLng(v)
    Case "longlong"
        CType = CLngLng(v)
    Case "single"
        CType = CSng(v)
    Case "string"
        CType = CStr(v)
    Case Else
        CType = CStr(v)
    End Select
End Function

Public Function SelectAllTextInControl(ctrl As Control)
    ctrl.SelStart = 0
    ctrl.SelLength = Len(ctrl.Text)
End Function

Attribute VB_Name = "UserSettings"
Option Explicit

Private Const cnstSettingsFolderName As String = "ShipConstructor Community Tools"
Private Const cnstSCLHoleFileName As String = "sclhole.txt"
Private Const cnstSCSpBombFileName As String = "scspbomb.txt"
Private Const cnstSCRemoveEnvFileName As String = "scremoveenv.txt"
Private Const cnstSCMDPostProcFileName As String = "scmdpostproc.txt"
Private Const cnstSCMDPostProcItemsFileName As String = "scmdpostprocitems.txt"

'----------------------------
'      Lightening Hole
'----------------------------
Public Function LoadSettings_CTLightHole(Optional bIsDefault As Boolean = False) As Collection
    Dim cData As Collection
        
    Set cData = New Collection
    
    If bIsDefault Or Not ReadFile(cnstSCLHoleFileName, cData) Then
        Set cData = New Collection
        cData.Add ("") 'version of the data file, not applicable here
        cData.Add ("50") 'hole depth as percentage of web depth
        cData.Add ("60") 'hole length as percentage of spacing length
        cData.Add ("100") 'hole length as percentage of web depth
        cData.Add ("33") 'corner radius as percentage of hole depth
        cData.Add ("False") 'align the hole depth with the web depth
        cData.Add ("_Draft_Cut") 'default layer for output
    End If
    
    Set LoadSettings_CTLightHole = cData
End Function

Public Function SaveSettings_CTLightHole(cData As Collection) As Boolean
    WriteFile cnstSCLHoleFileName, cData
End Function

'----------------------------
'      Space Bomb
'----------------------------
Public Function LoadSettings_CTSpaceBomb(Optional bIsDefault As Boolean = False) As Collection
    Dim cData As Collection
        
    Set cData = New Collection
    
    If bIsDefault Or Not ReadFile(cnstSCSpBombFileName, cData) Then
        Set cData = New Collection
        cData.Add ("") 'version of the data file, not applicable here
        cData.Add ("_Space_Bomb") 'layer name
        cData.Add ("1") 'manual step size
        cData.Add ("False") 'auto step
    End If
    
    Set LoadSettings_CTSpaceBomb = cData
End Function

Public Function SaveSettings_CTSpaceBomb(cData As Collection) As Boolean
    WriteFile cnstSCSpBombFileName, cData
End Function

'----------------------------
'      Remove Envelopes
'----------------------------
Public Function LoadSettings_CTRemoveEnvelopes(Optional bIsDefault As Boolean = False) As Collection
    Dim cData As Collection
        
    Set cData = New Collection
    
    If bIsDefault Or Not ReadFile(cnstSCRemoveEnvFileName, cData) Then
        Set cData = New Collection
        cData.Add ("") 'version of the data file, not applicable here
    End If
    
    Set LoadSettings_CTRemoveEnvelopes = cData
End Function

Public Function SaveSettings_CTRemoveEnvelopes(cData As Collection) As Boolean
    WriteFile cnstSCRemoveEnvFileName, cData
End Function

'----------------------------
'      MD Post-Process
'----------------------------
Public Function LoadSettings_CTMDPostProcess(Optional bIsDefault As Boolean = False) As Collection
    Dim cData As Collection
        
    Set cData = New Collection
    
    If bIsDefault Or Not ReadFile(cnstSCMDPostProcFileName, cData) Then
        Set cData = New Collection
        cData.Add ("") 'version of the data file, not applicable here
        cData.Add ("") 'data file path
        cData.Add ("") 'guid column name
    End If
    
    Set LoadSettings_CTMDPostProcess = cData
End Function

Public Function SaveSettings_CTMDPostProcess(cData As Collection) As Boolean
    WriteFile cnstSCMDPostProcFileName, cData
End Function

'----------------------------
'      MD Post-Processing Items
'----------------------------
Public Function LoadSettings_CTMDPostProcessItems(Optional sFilePath As String = "") As Collection
    Dim cPostProcessItems As Collection
    Dim cItem As Collection
    Dim cConditions As Collection
    Dim cCond As Collection
    Dim cActions As Collection
    Dim cAct As Collection
    Dim s As String
    Dim nReadState As Integer
    Dim n As Integer
    Dim i As Integer
    Dim j As Integer
        
    Set cPostProcessItems = New Collection
    
    If sFilePath = "" Then
        sFilePath = GetDefaultSettingsFolderPath() & "\" & cnstSCMDPostProcItemsFileName
    End If
    
    If Not CheckFile(sFilePath, True) Then
        Set LoadSettings_CTMDPostProcessItems = cPostProcessItems
        Exit Function
    End If
    
    On Error GoTo errFile
    Open sFilePath For Input As #1
    On Error GoTo 0
    
    On Error GoTo errRead
    Line Input #1, s 'file version
    nReadState = 1
    
    Do While Not EOF(1)
        Line Input #1, s
        Select Case nReadState
        Case 1: 'item name
            If Not cItem Is Nothing Then cPostProcessItems.Add cItem
            Set cItem = New Collection
            cItem.Add s
            nReadState = 2
        Case 2: 'item description
            cItem.Add s
            nReadState = 3
        Case 3: 'condition count
            Set cConditions = New Collection
            n = CInt(s)
            For i = 1 To n
                Set cCond = New Collection
                For j = 1 To 4
                    Line Input #1, s
                    cCond.Add s
                Next j
                cConditions.Add cCond
            Next i
            
            cItem.Add cConditions
            nReadState = 4
        Case 4: 'action count
            Set cActions = New Collection
            n = CInt(s)
            For i = 1 To n
                Set cAct = New Collection
                For j = 1 To 6
                    Line Input #1, s
                    cAct.Add s
                Next j
                cActions.Add cAct
            Next i
            
            cItem.Add cActions
            nReadState = 1
        End Select
    Loop
    On Error GoTo 0
    
    If Not cItem Is Nothing Then
        cPostProcessItems.Add cItem
    End If
    
    Close #1
    
    Set LoadSettings_CTMDPostProcessItems = cPostProcessItems
    Exit Function
    
errFile:
    If Err.Number <> 0 Then
        s = "Error #" & Str(Err.Number) & " was generated by " & Err.Source & vbLf & vbLf & Err.Description
        MsgBox s, vbExclamation, "Error", Err.HelpFile, Err.HelpContext
    End If
    Set LoadSettings_CTMDPostProcessItems = New Collection
    Exit Function

errRead:
    CriticalMsg "LoadSettings_CTMDPostProcessItems", "Unable to read the data file containing post-processing data."
    Set LoadSettings_CTMDPostProcessItems = New Collection
    Close #1
    Exit Function
End Function

Public Function SaveSettings_CTMDPostProcessItems(cPostProcessItems As Collection, Optional sFilePath As String = "") As Boolean
    Dim cItem As Collection
    Dim cCondition As Variant
    Dim cAction As Variant
    Dim v As Variant
    Dim s As String
    
    If sFilePath = "" Then
        sFilePath = GetDefaultSettingsFolderPath() & "\" & cnstSCMDPostProcItemsFileName
    End If
    
    On Error GoTo errFile
    Open sFilePath For Output As #1
    On Error GoTo 0
    
    Print #1, "1" 'data version
    
    For Each cItem In cPostProcessItems
        Print #1, cItem(1)              'item name
        Print #1, cItem(2)              'item description
        Print #1, cItem(3).Count        '# of conditions
        For Each cCondition In cItem(3) 'conditions
            For Each v In cCondition
                Print #1, v
            Next v
        Next cCondition
        Print #1, cItem(4).Count        '# of actions
        For Each cAction In cItem(4)    'actions
            For Each v In cAction
                Print #1, v
            Next v
        Next cAction
    Next cItem
       
    Close #1
    
    SaveSettings_CTMDPostProcessItems = True
    Exit Function
    
errFile:
    If Err.Number <> 0 Then
        s = "Error #" & Str(Err.Number) & " was generated by " & Err.Source & vbLf & vbLf & Err.Description
        MsgBox s, vbExclamation, "Error", Err.HelpFile, Err.HelpContext
    End If
    SaveSettings_CTMDPostProcessItems = False
End Function

'------------------ General ------------------------------------
Private Function CheckFile(sFileName As String, Optional bIsFullPath As Boolean = False) As Boolean
    Dim sPath As String
    
    If bIsFullPath Then
        sPath = sFileName
    Else
        sPath = Environ("appdata") & "\SSI"
        If Dir(sPath, vbDirectory) = Empty Then
            MkDir (sPath)
        End If
        
        sPath = sPath & "\" & cnstSettingsFolderName
        If Dir(sPath, vbDirectory) = Empty Then
            MkDir (sPath)
        End If
        
        sPath = sPath & "\" & sFileName
    End If
    If Dir(sPath) = Empty Then
        CheckFile = False
    Else
        CheckFile = True
    End If
End Function

Private Function ReadFile(sFileName As String, ByRef cData As Collection) As Boolean
    Dim sPath As String
    Dim s As String
    
    If Not CheckFile(sFileName) Then
        ReadFile = False
        Exit Function
    End If
    
    sPath = GetDefaultSettingsFolderPath() & "\" & sFileName
    
    On Error GoTo errFile
    Open sPath For Input Access Read As #1
    On Error GoTo 0
    
    Do While Not EOF(1)
        Line Input #1, s
        cData.Add s
    Loop
    Close #1
    
    ReadFile = True
    Exit Function
    
errFile:
    If Err.Number <> 0 Then
        s = "Error #" & Str(Err.Number) & " was generated by " & Err.Source & vbLf & vbLf & Err.Description
        MsgBox s, vbExclamation, "Error", Err.HelpFile, Err.HelpContext
    End If
    Close #1
    ReadFile = False
End Function

Private Function WriteFile(sFileName As String, cData As Collection) As Boolean
    Dim sPath As String
    Dim i As Integer
    Dim s As String
    
    sPath = GetDefaultSettingsFolderPath() & "\" & sFileName
        
    On Error GoTo errFile
    Open sPath For Output As #1
    On Error GoTo 0
    
    For i = 1 To cData.Count
        Print #1, cData(i)
    Next i
    Close #1
    
    WriteFile = True
    Exit Function
    
errFile:
    If Err.Number <> 0 Then
        s = "Error #" & Str(Err.Number) & " was generated by " & Err.Source & vbLf & vbLf & Err.Description
        MsgBox s, vbExclamation, "Error", Err.HelpFile, Err.HelpContext
    End If
    WriteFile = False
    Close #1
End Function

Private Function GetDefaultSettingsFolderPath() As String
    GetDefaultSettingsFolderPath = Environ("appdata") & "\SSI\" & cnstSettingsFolderName
End Function

Attribute VB_Name = "acToolsLabels"
'Fields in the label XData:
'  1 - (1070 . 1) - Version of Label Specification (integer) - should be 1 to match this specification
'  2 - (1000 . "D6D6A0A4-EAE1-4741-BA87-E6FC5BA69EA0") - Part GUID of labelled part (string)
'  3 - (1005 . "B6E4") - AutoCAD handle of Viewport
'  4 - (1005 . "27615") - AutoCAD handle/object id of labelled object
'  5 - (1010 0.0 0.0 0.0) - Point on selected part
'  6 - (1000 . "5DE94C49-5219-4133-92E7-2E69B107EAE7") - BOM GUID
'  7 - (1070 . 1) - Is position locked

Option Explicit

Public Sub CTLabelHighlightOrphaned()
    Dim obj As Variant
    Dim sType As String
    Dim XDataType As Variant
    Dim XDataValue As Variant
    Dim selSet As AcadSelectionSet
    Dim ssobjs As Variant
    Dim cObjs As Collection
    Dim i As Integer
    
    Set cObjs = New Collection
        
    For Each selSet In ThisDrawing.SelectionSets
        If selSet.Name = "orthaned_label_temp" Then
            selSet.Delete
            Exit For
        End If
    Next selSet
    
    Set selSet = ThisDrawing.SelectionSets.Add("orthaned_label_temp")
        
    For Each obj In ThisDrawing.PaperSpace
        sType = TypeName(obj)
        If LCase(sType) = "isconlabelcomwrapper" Then
            obj.GetXData "", XDataType, XDataValue
            If XDataValue(3) = 0 And XDataValue(4) = 0 Then
                cObjs.Add obj
            End If
        End If
    Next obj
    
    If cObjs.Count > 0 Then
        ReDim ssobjs(0 To cObjs.Count - 1) As AcadEntity
        For i = 1 To cObjs.Count
            Set ssobjs(i - 1) = cObjs(i)
        Next i
        selSet.AddItems ssobjs
    End If
    
    ThisDrawing.Regen acAllViewports
    
    selSet.Highlight True
    selSet.Delete
End Sub

Attribute VB_Name = "ufLHoleOptions"
Attribute VB_Base = "0{722A1B51-1F75-4017-AAD7-838E6B3AB318}{670E672B-B5AC-4F3B-9752-B800F6759ADA}"
Attribute VB_GlobalNameSpace = False
Attribute VB_Creatable = False
Attribute VB_PredeclaredId = True
Attribute VB_Exposed = False
Attribute VB_TemplateDerived = False
Attribute VB_Customizable = False
Option Explicit

Private Sub bttnDefault_Click()
    LoadData True
End Sub

Private Sub UserForm_Activate()
    LoadData False
End Sub

Private Sub bttnOK_Click()
    SaveData
    Hide
End Sub

Private Sub bttnOK_KeyPress(ByVal KeyAscii As MSForms.ReturnInteger)
    If KeyAscii = 27 Then
        bttnCancel_Click
    End If
End Sub

Private Sub bttnCancel_Click()
    Hide
End Sub

Private Sub tbCRHD_Change()
    ValidateEntry (tbCRHD.Name)
End Sub

Private Sub tbHDWD_Change()
    ValidateEntry (tbHDWD.Name)
End Sub

Private Sub tbHLSP_Change()
    ValidateEntry (tbHLSP.Name)
End Sub

Private Sub tbHLWD_Change()
    ValidateEntry (tbHLWD.Name)
End Sub


Private Function ValidateEntry(tbName As String)
    Dim i As Integer
    Dim c As String
    Dim s As String
    Dim tb As TextBox
    
    Set tb = Me(tbName)
        
    s = ""
    For i = 1 To Len(tb.Text)
        c = Mid(tb.Text, i, 1)
        If InStr("0123456789", c) Then
            s = s & c
        End If
    Next i
    
    If s <> tb.Text Then
        tb.Text = s
    End If
End Function

Private Sub LoadData(bIsDefault As Boolean)
    Dim c As Collection
        
    Set c = LoadSettings_CTLightHole(bIsDefault)
    If c.Count > 1 Then tbHDWD.Value = c(2)
    If c.Count > 2 Then tbHLSP.Value = c(3)
    If c.Count > 3 Then tbHLWD.Value = c(4)
    If c.Count > 4 Then tbCRHD.Value = c(5)
    If c.Count > 5 Then cboxAlignWeb.Value = c(6)
    If c.Count > 6 Then tbLayerName.Value = c(7)
End Sub

Private Sub SaveData()
    Dim c As Collection
        
    Set c = New Collection
    
    c.Add ("1")
    c.Add (tbHDWD.Text)
    c.Add (tbHLSP.Text)
    c.Add (tbHLWD.Text)
    c.Add (tbCRHD.Text)
    c.Add (cboxAlignWeb.Value)
    c.Add (tbLayerName.Text)
    
    SaveSettings_CTLightHole c
End Sub

Attribute VB_Name = "ufMDPostProcess"
Attribute VB_Base = "0{2AFE2090-E124-4BDC-9338-0284CA5C5FEF}{2A7CB0F9-6DEF-4403-8EBA-DCB270DD2D23}"
Attribute VB_GlobalNameSpace = False
Attribute VB_Creatable = False
Attribute VB_PredeclaredId = True
Attribute VB_Exposed = False
Attribute VB_TemplateDerived = False
Attribute VB_Customizable = False
Option Explicit


'----------- cPostProcessItem --------------
' Name
' Description
' cConditions
' cActions
Public cPostProcessItems As Collection
Public bIsCancel As Boolean
Public cTSVHeaders As Collection

Private bIsFirstActivate As Boolean
Private cSCData As Collection

Private Sub bttnAdd_Click()
    AddOrEditItem True
End Sub

Private Sub bttnBrowseDataFile_Click()
    Dim sPath As String
    
    sPath = GetFolderPath(tbDataFilePath.Text)
    sPath = FileBrowseOpen(sPath, "Select File", "TSV Files (*.tsv)|*.tsv|All Files (*.*)|*.*", 0, GetUserformHwnd(Me))
            
    If sPath <> "" Then
        tbDataFilePath.Text = sPath
    End If
End Sub

Private Sub bttnClose_Click()
    Hide
End Sub

Private Sub bttnCopy_Click()
    Dim cItem As Collection
    Dim s As String
    Dim v As Variant
    
    If lboxPostProcessItems.ListIndex < 0 Then
        Exit Sub
    End If
    
    'copy element
    Set cItem = CloneCollectionItem(cPostProcessItems(lboxPostProcessItems.ListIndex + 1))
    
    'rename
    s = "Copy of " & cItem(1)
    cItem.Remove 1
    cItem.Add s, , 1
    
    'add
    cPostProcessItems.Add cItem
    
    'update list
    UpdateItemsList cItem, True
    lboxPostProcessItems.ListIndex = lboxPostProcessItems.ListCount - 1
    
    'open for edit
    AddOrEditItem False
End Sub

Private Sub bttnDown_Click()
    Dim cItem As Collection
    Dim i As Integer
    
    If lboxPostProcessItems.ListIndex < 0 Or lboxPostProcessItems.ListIndex + 1 = lboxPostProcessItems.ListCount Then
        Exit Sub
    End If
    
    i = lboxPostProcessItems.ListIndex
    
    Set cItem = cPostProcessItems(i + 1)
    cPostProcessItems.Remove i + 1
    cPostProcessItems.Add cItem, , , i + 1
    
    ReloadPostProcessingItems
    lboxPostProcessItems.ListIndex = i + 1
    bttnDown.SetFocus
End Sub

Private Sub bttnEdit_Click()
    AddOrEditItem False
End Sub

Private Sub AddOrEditItem(bIsAddNew As Boolean)
    Dim uf As ufMDPostProcessItem
    Dim cItem As Collection
    
    If Not bIsAddNew Then
        If lboxPostProcessItems.ListIndex < 0 Then
            Exit Sub
        End If
    End If
    
    Set uf = New ufMDPostProcessItem
    Set uf.cSCHeaders = cTSVHeaders
    
    If Not bIsAddNew Then
        uf.tbName.Text = cPostProcessItems(lboxPostProcessItems.ListIndex + 1)(1)
        uf.tbDescription.Text = cPostProcessItems(lboxPostProcessItems.ListIndex + 1)(2)
        Set uf.cConditions = cPostProcessItems(lboxPostProcessItems.ListIndex + 1)(3)
        Set uf.cActions = cPostProcessItems(lboxPostProcessItems.ListIndex + 1)(4)
    Else
        uf.tbName.Text = "New Item"
    End If
        
    uf.show
    If uf.bIsCancel Then
        Unload uf
        Exit Sub
    End If
    
    If bIsAddNew Then
        Set cItem = New Collection
        cItem.Add uf.tbName.Text
        cItem.Add uf.tbDescription.Text
        cItem.Add uf.cConditions
        cItem.Add uf.cActions
        cPostProcessItems.Add cItem
        UpdateItemsList cItem, True
        lboxPostProcessItems.ListIndex = lboxPostProcessItems.ListCount - 1
    Else
        Set cItem = New Collection
        cItem.Add uf.tbName.Text
        cItem.Add uf.tbDescription.Text
        cItem.Add uf.cConditions
        cItem.Add uf.cActions
        
        cPostProcessItems.Add cItem, , lboxPostProcessItems.ListIndex + 1
        cPostProcessItems.Remove lboxPostProcessItems.ListIndex + 2
        UpdateItemsList cItem, False
    End If
    
    Unload uf
End Sub

Private Sub UpdateItemsList(cItem As Collection, bIsAddNew As Boolean)
    Dim i As Integer
    If cItem.Count = 4 Then
        If bIsAddNew Then
            lboxPostProcessItems.AddItem
            i = lboxPostProcessItems.ListCount - 1
        Else
            i = lboxPostProcessItems.ListIndex
            If i < 0 Then
                CriticalMsg "UpdateItemsList", "Unable to edit the item."
                Exit Sub
            End If
        End If
        
        lboxPostProcessItems.List(i, 0) = cItem(1)
        lboxPostProcessItems.List(i, 1) = cItem(2)
    Else
        CriticalMsg "UpdateItemsList", "Unable to process the item."
    End If
End Sub

Private Sub bttnImport_Click()
    LoadItems True
End Sub

Private Sub bttnLoad_Click()
    LoadItems False
End Sub

Private Sub LoadItems(bIsAppend As Boolean)
    Dim sPath As String
    Dim cTemp As Collection
    Dim v As Variant
    
    sPath = FileBrowseOpen(sPath, "Select File", "Text Files (*.txt)|*.txt|All Files (*.*)|*.*", 0, GetUserformHwnd(Me))
            
    If sPath <> "" Then
        If bIsAppend Then
            Set cTemp = LoadSettings_CTMDPostProcessItems(sPath)
            For Each v In cTemp
                cPostProcessItems.Add v
            Next v
        Else
            Set cPostProcessItems = LoadSettings_CTMDPostProcessItems(sPath)
        End If
        
        ReloadPostProcessingItems
    End If
End Sub

Private Sub bttnRemove_Click()
    Dim i As Integer
    
    i = lboxPostProcessItems.ListIndex
    If i >= 0 Then
        cPostProcessItems.Remove (i + 1)
        lboxPostProcessItems.RemoveItem i
        If i > 0 Then
            lboxPostProcessItems.ListIndex = i - 1
        Else
            If lboxPostProcessItems.ListCount > 0 Then
                lboxPostProcessItems.ListIndex = 0
            End If
        End If
    End If
    
    If lboxPostProcessItems.ListIndex < 0 Then lboxPostProcessItems_Change
End Sub

Private Sub bttnRun_Click()
    bIsCancel = False
    Hide
End Sub

Private Sub bttnSaveAs_Click()
    Dim sPath As String
    
    sPath = FileBrowseSave("", "", "Save As...", "Text Files (*.txt)|*.txt", 0, GetUserformHwnd(Me), "txt")
            
    If sPath <> "" Then
        SaveSettings_CTMDPostProcessItems cPostProcessItems, sPath
    End If
End Sub

Private Sub bttnUp_Click()
    Dim cItem As Collection
    Dim i As Integer
    
    If lboxPostProcessItems.ListIndex <= 0 Then
        Exit Sub
    End If
    
    i = lboxPostProcessItems.ListIndex
    
    Set cItem = cPostProcessItems(i + 1)
    cPostProcessItems.Remove i + 1
    cPostProcessItems.Add cItem, , i
    
    ReloadPostProcessingItems
    lboxPostProcessItems.ListIndex = i - 1
    bttnUp.SetFocus
End Sub

Private Sub lboxPostProcessItems_Change()
    If lboxPostProcessItems.ListIndex = -1 Then
        bttnEdit.Enabled = False
    Else
        bttnEdit.Enabled = True
    End If
    
    bttnCopy.Enabled = bttnEdit.Enabled
    bttnRemove.Enabled = bttnEdit.Enabled
    bttnUp.Enabled = bttnEdit.Enabled
    bttnDown.Enabled = bttnEdit.Enabled
End Sub

Private Sub lboxPostProcessItems_DblClick(ByVal Cancel As MSForms.ReturnBoolean)
    If lboxPostProcessItems.ListIndex >= 0 Then
        AddOrEditItem False
    End If
End Sub

Private Sub UserForm_Activate()
    Dim cData As Collection
    
    If bIsFirstActivate Then
        bttnRun.Enabled = False
        
        Set cData = LoadSettings_CTMDPostProcess()
        If cData.Count < 3 Then
            Set cData = LoadSettings_CTMDPostProcess(True)
        End If
        tbDataFilePath.Text = cData(2)
        If Not FileExists(tbDataFilePath.Text) Then
            tbDataFilePath.Text = ""
        Else
            cboxGuid.Text = cData(3)
        End If
                
        bIsFirstActivate = False
        If cPostProcessItems Is Nothing Then
            Set cPostProcessItems = LoadSettings_CTMDPostProcessItems()
            ReloadPostProcessingItems
        End If
        
        lboxPostProcessItems_Change
        If bttnRun.Enabled Then bttnRun.SetFocus
    End If
End Sub

Private Sub ReloadPostProcessingItems()
    Dim cItem As Collection
    
    lboxPostProcessItems.Clear
    For Each cItem In cPostProcessItems
        UpdateItemsList cItem, True
    Next cItem
End Sub

Private Sub tbDataFilePath_Change()
    cboxGuid.Clear
    If FileExists(tbDataFilePath.Text) Then
        ReloadSCHeaders
    Else
        bttnRun.Enabled = False
    End If
End Sub

Private Sub ReloadSCHeaders()
    Dim v As Variant
    
    Set cTSVHeaders = ReadTSVHeaders(tbDataFilePath.Text)
    If cTSVHeaders Is Nothing Then
        bttnRun.Enabled = False
    Else
        If cTSVHeaders.Count < 2 Then
            bttnRun.Enabled = False
        Else
            If lblViewsCount.Caption <> "0" Then bttnRun.Enabled = True
        End If
    End If
        
    For Each v In cTSVHeaders
        cboxGuid.AddItem v
    Next v
    If cboxGuid.ListCount > 0 Then
        cboxGuid.ListIndex = 0
    End If
    
End Sub

Private Sub UserForm_Initialize()
    bIsCancel = True
    bIsFirstActivate = True
End Sub

Private Sub UserForm_QueryClose(Cancel As Integer, CloseMode As Integer)
    Dim cData As Collection
    Set cData = New Collection

    cData.Add "1"                   'version
    cData.Add tbDataFilePath.Text   'data file path
    cData.Add cboxGuid.Text
    
    SaveSettings_CTMDPostProcess cData
    SaveSettings_CTMDPostProcessItems cPostProcessItems
End Sub

Attribute VB_Name = "ufMDPostProcessAction"
Attribute VB_Base = "0{F3328466-1292-46A8-98D8-600358BE74C4}{DBFD9CED-0905-477E-B239-FC6ECDB247AC}"
Attribute VB_GlobalNameSpace = False
Attribute VB_Creatable = False
Attribute VB_PredeclaredId = True
Attribute VB_Exposed = False
Attribute VB_TemplateDerived = False
Attribute VB_Customizable = False
Public bIsCancel As Boolean
Public cSCHeaders As Collection

'------ cAction -------
'Target Type - Enum
'Target Name - String
'Action - Enum
'Value - String
'IsSCProperty - Bool
Public cAction As Collection

Private bIsFirstActivate As Boolean

Private Sub bttnCancel_Click()
    Hide
End Sub

Private Sub bttnOK_Click()
     If Trim(cboxTarget.Text) = "" Then
        WarningMsg "The target name cannot be empty."
        Exit Sub
    End If
    
    Set cAction = New Collection
    
    cAction.Add cboxType.ListIndex
    cAction.Add cboxTarget.Text
    cAction.Add cboxAction.ListIndex
    cAction.Add checkIsSCProp.Value
    cAction.Add cboxValue.Value
    cAction.Add tbValue.Text
    
    bIsCancel = False
    Hide
End Sub

Private Sub cboxType_Change()
    ReloadTargets
End Sub

Private Sub ReloadTargets()
    Dim cValues As Collection
        
    Set cValues = New Collection
        
    Select Case cboxType.ListIndex
        Case mdpp_target_type_object
            cboxTarget.Enabled = False
            cboxTarget.MatchRequired = True
            
            cValues.Add "Object"
            UpdateCBoxContent cboxTarget, cValues
            
            Set cValues = New Collection
            cValues.Add "Delete"
            cValues.Add "Unmodify"
            
            UpdateCBoxContent cboxAction, cValues
            
        Case mdpp_target_type_acad_property
            cboxTarget.Enabled = True
            cboxTarget.MatchRequired = False
            cValues.Add "Color"
            cValues.Add "Layer"
            cValues.Add "Linetype"
            cValues.Add "LinetypeScale"
            cValues.Add "Lineweight"
            cValues.Add "Thickness"
            UpdateCBoxContent cboxTarget, cValues
            
            Set cValues = New Collection
            cValues.Add "Set to"
            UpdateCBoxContent cboxAction, cValues
    End Select
End Sub

Private Sub UpdateCBoxContent(cbox As ComboBox, cValues As Collection)
    Dim s As Variant
    
    cbox.Clear
    cbox.Value = ""
    
    If cValues Is Nothing Then Exit Sub
    
    For Each s In cValues
        cbox.AddItem s
    Next s
    
    If cbox.ListCount > 0 Then cbox.ListIndex = 0
End Sub


Private Sub cboxValue_Change()
    UpdateActionValue
End Sub

Private Sub checkIsSCProp_Click()
    cboxValue.Enabled = checkIsSCProp.Value
    UpdateActionValue
End Sub

Private Sub UpdateActionValue()
    If cboxValue.Enabled Then
        lblSampleValue.Caption = cboxValue.Text & tbValue.Text
    Else
        lblSampleValue.Caption = tbValue.Text
    End If
End Sub

Private Sub tbValue_Change()
    UpdateActionValue
End Sub

Private Sub UserForm_Activate()
    If bIsFirstActivate Then
        'cboxType
        cboxType.AddItem "Object"           'mdpp_target_type_object
        cboxType.AddItem "ACAD Property"    'mdpp_target_type_acad_property
        cboxType.ListIndex = 0
        
        'cboxValue
        cboxValue_UpdateList cSCHeaders
                        
        'action
        If Not cAction Is Nothing Then
            cboxType.ListIndex = cAction(1)         'target type
            cboxTarget.Text = cAction(2)            'target name
            cboxAction.ListIndex = cAction(3)       'target action
            checkIsSCProp.Value = cAction(4)        'is the SC property component enabled
            cboxValue.Value = cAction(5)            'SC Property
            tbValue.Text = cAction(6)               'user-entered value
        Else
            checkIsSCProp.Value = False
        End If
                
        checkIsSCProp_Click
        
        SelectAllTextInControl cboxType
        cboxType.SetFocus
        
        bIsFirstActivate = False
    End If
End Sub

Private Sub UserForm_Initialize()
    bIsCancel = True
    bIsFirstActivate = True
End Sub

Private Sub cboxValue_UpdateList(cValues As Collection)
    Dim s As Variant
    
    cboxValue.Clear
    cboxValue.Value = ""
    
    If cValues Is Nothing Then Exit Sub
    
    For Each s In cValues
        cboxValue.AddItem s
    Next s
        
    If cboxValue.ListCount > 0 Then cboxValue.ListIndex = 0
End Sub

Attribute VB_Name = "ufMDPostProcessCondition"
Attribute VB_Base = "0{85CDA4B5-BB2B-4126-9CB9-007E922687CA}{77E7F5DE-FF86-4004-B2C8-8E40DC659B97}"
Attribute VB_GlobalNameSpace = False
Attribute VB_Creatable = False
Attribute VB_PredeclaredId = True
Attribute VB_Exposed = False
Attribute VB_TemplateDerived = False
Attribute VB_Customizable = False
Public bIsCancel As Boolean
Public cSCHeaders As Collection

'------ cCondition -------
'Parameter Type - Enum
'Parameter Name - String
'Condition - Enum
'Value - String
Public cCondition As Collection

Private bIsFirstActivate As Boolean

Private Sub bttnCancel_Click()
    Hide
End Sub

Private Sub bttnOK_Click()
    If Trim(cboxParameter.Text) = "" Then
        WarningMsg "The parameter name cannot be empty."
        Exit Sub
    End If
    
    Set cCondition = New Collection
    
    cCondition.Add cboxType.ListIndex
    cCondition.Add cboxParameter.Text
    cCondition.Add cboxCondition.ListIndex
    cCondition.Add tbValue.Text
    
    bIsCancel = False
    Hide
End Sub


Private Sub cboxCondition_Change()

End Sub

Private Sub cboxType_Change()
    ReloadParams
End Sub

Private Sub UserForm_Activate()
    If bIsFirstActivate Then
        'cboxType
        cboxType.AddItem "SC"
        cboxType.AddItem "ACAD"
        cboxType.AddItem "MD"
        cboxType.ListIndex = 0
        
        'cboxCondition
        cboxCondition.AddItem "Equals"
        cboxCondition.AddItem "Does not equal"
        cboxCondition.AddItem "Starts with"
        cboxCondition.AddItem "Contains"
        cboxCondition.AddItem "Does not contain"
        cboxCondition.AddItem "Less than"
        cboxCondition.AddItem "Greater than"
        cboxCondition.ListIndex = 0
        
        'condition
        If Not cCondition Is Nothing Then
            cboxType.ListIndex = cCondition(1)
            cboxParameter.Text = cCondition(2)
            cboxCondition.ListIndex = cCondition(3)
            tbValue.Text = cCondition(4) ' value
        End If
        
        SelectAllTextInControl cboxType
        cboxType.SetFocus
        bIsFirstActivate = False
    End If
End Sub

Private Sub ReloadParams()
    Dim cParams As Collection
    
    Set cParams = New Collection
    
    Select Case cboxType.ListIndex
        Case mdpp_prop_type_sc
            cboxParameter.MatchRequired = False
            cboxParameter_UpdateList cSCHeaders
        Case mdpp_prop_type_acad
            cboxParameter.MatchRequired = False
            cParams.Add "Color"
            cParams.Add "Layer"
            cParams.Add "Length"
            cParams.Add "Linetype"
            cParams.Add "LinetypeScale"
            cParams.Add "Lineweight"
            cParams.Add "Object Type"
            cParams.Add "Thickness"
            
            cboxParameter_UpdateList cParams
        Case mdpp_prop_type_md
            cboxParameter.MatchRequired = True
            cParams.Add "Modified"
            cboxParameter_UpdateList cParams
    End Select
End Sub

Private Sub cboxParameter_UpdateList(cParams As Collection)
    Dim s As Variant
    
    cboxParameter.Clear
    cboxParameter.Value = ""
    
    If cParams Is Nothing Then Exit Sub
    
    For Each s In cParams
        cboxParameter.AddItem s
    Next s
        
    If cboxParameter.ListCount > 0 Then cboxParameter.ListIndex = 0
End Sub

Private Sub UserForm_Initialize()
    bIsCancel = True
    bIsFirstActivate = True
End Sub

Attribute VB_Name = "ufMDPostProcessItem"
Attribute VB_Base = "0{CB20682F-7833-41C3-9EEA-6F422075833F}{1D95520A-9ADB-4F10-A9CE-233A7B011BEF}"
Attribute VB_GlobalNameSpace = False
Attribute VB_Creatable = False
Attribute VB_PredeclaredId = True
Attribute VB_Exposed = False
Attribute VB_TemplateDerived = False
Attribute VB_Customizable = False
Option Explicit

Public bIsCancel As Boolean
Public cSCHeaders As Collection
Public cConditions As Collection
Public cActions As Collection

Private bIsFirstActivate As Boolean

Private Sub bttnAddAction_Click()
    AddOrEditAction True
End Sub

Private Sub bttnAddCondition_Click()
    AddOrEditCondition True
End Sub

Private Sub bttnCancel_Click()
    Hide
End Sub

Private Sub bttnCopyAction_Click()
    Dim cItem As Collection
    Dim v As Variant
    
    If lboxActions.ListIndex < 0 Then
        Exit Sub
    End If
    
    'copy element
    Set cItem = CloneCollectionItem(cActions(lboxActions.ListIndex + 1))
       
    'add
    cActions.Add cItem
    
    'update list
    UpdateActionsList cItem, True
    lboxActions.ListIndex = lboxActions.ListCount - 1
    
    'open for edit
    AddOrEditAction False
End Sub

Private Sub bttnCopyCondition_Click()
    Dim cItem As Collection
    Dim v As Variant
    
    If lboxConditions.ListIndex < 0 Then
        Exit Sub
    End If
    
    'copy element
    Set cItem = CloneCollectionItem(cConditions(lboxConditions.ListIndex + 1))
       
    'add
    cConditions.Add cItem
    
    'update list
    UpdateConditionsList cItem, True
    lboxConditions.ListIndex = lboxConditions.ListCount - 1
    
    'open for edit
    AddOrEditCondition False
End Sub

Private Sub bttnDownAction_Click()
    Dim cItem As Collection
    Dim i As Integer
    
    If lboxActions.ListIndex < 0 Or lboxActions.ListIndex + 1 = lboxActions.ListCount Then
        Exit Sub
    End If
    
    i = lboxActions.ListIndex
    
    Set cItem = cActions(i + 1)
    cActions.Remove i + 1
    cActions.Add cItem, , , i + 1
    
    ReloadActions
    lboxActions.ListIndex = i + 1
    bttnDownAction.SetFocus
End Sub

Private Sub bttnDownCondition_Click()
    Dim cItem As Collection
    Dim i As Integer
    
    If lboxConditions.ListIndex < 0 Or lboxConditions.ListIndex + 1 = lboxConditions.ListCount Then
        Exit Sub
    End If
    
    i = lboxConditions.ListIndex
    
    Set cItem = cConditions(i + 1)
    cConditions.Remove i + 1
    cConditions.Add cItem, , , i + 1
    
    ReloadConditions
    lboxConditions.ListIndex = i + 1
    bttnDownCondition.SetFocus
End Sub

Private Sub bttnEditAction_Click()
    AddOrEditAction False
End Sub

Private Sub bttnEditCondition_Click()
    AddOrEditCondition False
End Sub

Private Sub AddOrEditAction(bIsAddNew As Boolean)
    Dim uf As ufMDPostProcessAction
            
    If Not bIsAddNew Then
        If lboxActions.ListIndex < 0 Then
            Exit Sub
        End If
    End If
            
    Set uf = New ufMDPostProcessAction
    Set uf.cSCHeaders = cSCHeaders
        
    If Not bIsAddNew Then
        Set uf.cAction = cActions(lboxActions.ListIndex + 1)
    End If
    
    uf.show
    If uf.bIsCancel Then
        Unload uf
        Exit Sub
    End If
    
    If bIsAddNew Then
        cActions.Add uf.cAction
        UpdateActionsList uf.cAction, True
        lboxActions.ListIndex = lboxActions.ListCount - 1
    Else
        cActions.Add uf.cAction, , lboxActions.ListIndex + 1
        cActions.Remove lboxActions.ListIndex + 2
        UpdateActionsList cActions(lboxActions.ListIndex + 1), False
    End If
        
    Unload uf
End Sub

Private Sub AddOrEditCondition(bIsAddNew As Boolean)
    Dim uf As ufMDPostProcessCondition
            
    If Not bIsAddNew Then
        If lboxConditions.ListIndex < 0 Then
            Exit Sub
        End If
    End If
            
    Set uf = New ufMDPostProcessCondition
    Set uf.cSCHeaders = cSCHeaders
    
    If Not bIsAddNew Then
        Set uf.cCondition = cConditions(lboxConditions.ListIndex + 1)
    End If
    
    uf.show
    If uf.bIsCancel Then
        Unload uf
        Exit Sub
    End If
    
    If bIsAddNew Then
        cConditions.Add uf.cCondition
        UpdateConditionsList uf.cCondition, True
        lboxConditions.ListIndex = lboxConditions.ListCount - 1
    Else
        cConditions.Add uf.cCondition, , lboxConditions.ListIndex + 1
        cConditions.Remove lboxConditions.ListIndex + 2
        UpdateConditionsList cConditions(lboxConditions.ListIndex + 1), False
    End If
        
    Unload uf
End Sub

Private Sub bttnOK_Click()
    bIsCancel = False
    Hide
End Sub

Private Sub bttnRemoveAction_Click()
    Dim i As Integer
    
    i = lboxActions.ListIndex
    If i >= 0 Then
        cActions.Remove (i + 1)
        lboxActions.RemoveItem i
        If i > 0 Then
            lboxActions.ListIndex = i - 1
        Else
            If lboxActions.ListCount > 0 Then
                lboxActions.ListIndex = 0
            End If
        End If
    End If
    
    If lboxActions.ListIndex < 0 Then lboxActions_Change
End Sub

Private Sub bttnRemoveCondition_Click()
    Dim i As Integer
    
    i = lboxConditions.ListIndex
    If i >= 0 Then
        cConditions.Remove (i + 1)
        lboxConditions.RemoveItem i
        If i > 0 Then
            lboxConditions.ListIndex = i - 1
        Else
            If lboxConditions.ListCount > 0 Then
                lboxConditions.ListIndex = 0
            End If
        End If
    End If
    
    If lboxConditions.ListIndex < 0 Then lboxConditions_Change
End Sub

Private Sub bttnUpAction_Click()
    Dim cItem As Collection
    Dim i As Integer
    
    If lboxActions.ListIndex <= 0 Then
        Exit Sub
    End If
    
    i = lboxActions.ListIndex
    
    Set cItem = cActions(i + 1)
    cActions.Remove i + 1
    cActions.Add cItem, , i
    
    ReloadActions
    lboxActions.ListIndex = i - 1
    bttnUpAction.SetFocus
End Sub

Private Sub bttnUpCondition_Click()
    Dim cItem As Collection
    Dim i As Integer
    
    If lboxConditions.ListIndex <= 0 Then
        Exit Sub
    End If
    
    i = lboxConditions.ListIndex
    
    Set cItem = cConditions(i + 1)
    cConditions.Remove i + 1
    cConditions.Add cItem, , i
    
    ReloadConditions
    lboxConditions.ListIndex = i - 1
    bttnUpCondition.SetFocus
End Sub

Private Sub ReloadActions()
    Dim cItem As Collection
    
    lboxActions.Clear
    For Each cItem In cActions
        UpdateActionsList cItem, True
    Next cItem
End Sub

Private Sub ReloadConditions()
    Dim cItem As Collection
    
    lboxConditions.Clear
    For Each cItem In cConditions
        UpdateConditionsList cItem, True
    Next cItem
End Sub

Private Sub lboxActions_Change()
    If lboxActions.ListIndex = -1 Then
        bttnEditAction.Enabled = False
    Else
        bttnEditAction.Enabled = True
    End If
    
    bttnCopyAction.Enabled = bttnEditAction.Enabled
    bttnRemoveAction.Enabled = bttnEditAction.Enabled
    bttnUpAction.Enabled = bttnEditAction.Enabled
    bttnDownAction.Enabled = bttnEditAction.Enabled
End Sub

Private Sub lboxActions_DblClick(ByVal Cancel As MSForms.ReturnBoolean)
    If lboxActions.ListIndex >= 0 Then
        AddOrEditAction False
    End If
End Sub

Private Sub lboxConditions_Change()
     If lboxConditions.ListIndex = -1 Then
        bttnEditCondition.Enabled = False
    Else
        bttnEditCondition.Enabled = True
    End If
    bttnCopyCondition.Enabled = bttnEditCondition.Enabled
    bttnRemoveCondition.Enabled = bttnEditCondition.Enabled
    bttnUpCondition.Enabled = bttnEditCondition.Enabled
    bttnDownCondition.Enabled = bttnEditCondition.Enabled
End Sub

Private Sub lboxConditions_DblClick(ByVal Cancel As MSForms.ReturnBoolean)
    If lboxConditions.ListIndex >= 0 Then
        AddOrEditCondition False
    End If
End Sub


Private Sub MultiPage1_Change()
    lblPageTitle.Caption = UCase("  " & MultiPage1.Pages(MultiPage1.Value).Caption)
    Select Case MultiPage1.Value
    Case 0
        lblPageTitle.BackColor = &H80000010
    Case 1
        lblPageTitle.BackColor = &H8000&
    Case 2
        lblPageTitle.BackColor = &H80&
    End Select
End Sub

Private Sub UserForm_Activate()
    Dim v As Collection
    
    If bIsFirstActivate Then
        MultiPage1.Value = 0
        If cConditions Is Nothing Then Set cConditions = New Collection
        If cActions Is Nothing Then Set cActions = New Collection
        
        For Each v In cConditions
            UpdateConditionsList v, True
        Next v
        For Each v In cActions
            UpdateActionsList v, True
        Next v
        
        lboxActions_Change
        lboxConditions_Change
        
        SelectAllTextInControl tbName
        tbName.SetFocus
        
        bIsFirstActivate = False
    End If
End Sub

Private Sub UpdateConditionsList(cCondition As Collection, bIsAddNew As Boolean)
    Dim i As Integer
    If cCondition.Count = 4 Then
        If bIsAddNew Then
            lboxConditions.AddItem
            i = lboxConditions.ListCount - 1
        Else
            i = lboxConditions.ListIndex
            If i < 0 Then
                CriticalMsg "UpdateConditionsList", "Unable to edit the condition."
                Exit Sub
            End If
        End If
        
        'type
        Select Case cCondition(1)
        Case mdpp_prop_type_sc
            lboxConditions.List(i, 0) = "SC"
        Case mdpp_prop_type_acad
            lboxConditions.List(i, 0) = "ACAD"
        Case mdpp_prop_type_md
            lboxConditions.List(i, 0) = "MD"
        End Select
        
        'parameter
        lboxConditions.List(i, 1) = cCondition(2)
        
        'condition
        Select Case cCondition(3)
        Case mdpp_cond_type_equals
            lboxConditions.List(i, 2) = "equals"
        Case mdpp_cond_type_does_not_equal
            lboxConditions.List(i, 2) = "does not equal"
        Case mdpp_cond_type_starts_with
            lboxConditions.List(i, 2) = "starts with"
        Case mdpp_cond_type_contains
            lboxConditions.List(i, 2) = "contains"
        Case mdpp_cond_type_does_not_contain
            lboxConditions.List(i, 2) = "does not contain"
        Case mdpp_cond_type_less_than
            lboxConditions.List(i, 2) = "less than"
        Case mdpp_cond_type_greater_than
            lboxConditions.List(i, 2) = "greater than"
        End Select
        
        'value
        lboxConditions.List(i, 3) = cCondition(4)
    Else
        CriticalMsg "UpdateConditionsList", "Unable to process the condition."
    End If
End Sub

Private Sub UpdateActionsList(cAction As Collection, bIsAddNew As Boolean)
    Dim i As Integer
    If cAction.Count = 6 Then
        If bIsAddNew Then
            lboxActions.AddItem
            i = lboxActions.ListCount - 1
        Else
            i = lboxActions.ListIndex
            If i < 0 Then
                CriticalMsg "UpdateActionsList", "Unable to edit the action."
                Exit Sub
            End If
        End If
        
        'type
        Select Case cAction(1)
        Case mdpp_target_type_object
            lboxActions.List(i, 0) = "Object"
            'action
            Select Case cAction(3)
            Case mdpp_act_obj_delete
                lboxActions.List(i, 2) = "Delete"
            Case mdpp_act_obj_unmodify
                lboxActions.List(i, 2) = "Unmodify"
            End Select
            'value
            lboxActions.List(i, 3) = "n/a"
        Case mdpp_target_type_acad_property
            lboxActions.List(i, 0) = "ACAD Property"
            'action
            Select Case cAction(3)
            Case mdpp_act_acad_prop_set_to
                lboxActions.List(i, 2) = "Set to"
            End Select
            'value
            If cAction(4) Then
                lboxActions.List(i, 3) = cAction(5) & cAction(6)
            Else
                lboxActions.List(i, 3) = cAction(6)
            End If
        End Select
        
        'target
        lboxActions.List(i, 1) = cAction(2)
                       
        
    Else
        CriticalMsg "UpdateActionsList", "Unable to process the action."
    End If
End Sub

Private Sub UserForm_Initialize()
    bIsFirstActivate = True
    bIsCancel = True
End Sub

Attribute VB_Name = "ufProgress"
Attribute VB_Base = "0{C0C3FF5E-11FF-46D1-8AEF-49107A5ADF48}{3D2E1D6F-790B-4B83-90BB-CDAA6B6614DC}"
Attribute VB_GlobalNameSpace = False
Attribute VB_Creatable = False
Attribute VB_PredeclaredId = True
Attribute VB_Exposed = False
Attribute VB_TemplateDerived = False
Attribute VB_Customizable = False
Public bIsCancel As Boolean

Private Sub bttnCancel_Click()
    bIsCancel = True
    Hide
End Sub

Private Sub UserForm_Activate()
    bIsCancel = False
End Sub

Private Sub UserForm_QueryClose(Cancel As Integer, CloseMode As Integer)
    Cancel = Not bIsCancel
End Sub

Public Sub SetProgress(dblProgress As Double)
    lblProgressText.Caption = CStr(Round(100 * dblProgress, 0)) & "%"
    lblProgressBar.Width = lblProgressBack.Width * dblProgress
    DoEvents
End Sub

Public Sub SetStage(sStageDesc As String)
    lblStage.Caption = sStageDesc
    DoEvents
End Sub

Attribute VB_Name = "ufRemoveEnvelopes"
Attribute VB_Base = "0{3DF57EE4-FD50-4EBA-A34A-7C2C7A395597}{E8A48630-E0A1-4073-AA13-7B16183F081C}"
Attribute VB_GlobalNameSpace = False
Attribute VB_Creatable = False
Attribute VB_PredeclaredId = True
Attribute VB_Exposed = False
Attribute VB_TemplateDerived = False
Attribute VB_Customizable = False
Option Explicit

Public cKeywords As Collection
Public bIsCancel As Boolean

Private Sub bttnAdd_Click()
    Dim s As String
    s = InputBox("Enter the text to search for in the layer name.", "Add Keyword", "_env")
    s = Trim(s)
    If Trim(s) <> "" Then
        lboxKeywords.AddItem s
    End If
    lboxKeywords_Change
End Sub

Private Sub bttnCancel_Click()
    SaveData
    Hide
End Sub

Private Sub bttnDelete_Click()
    If lboxKeywords.ListIndex < 0 Then
        Exit Sub
    End If
    lboxKeywords.RemoveItem lboxKeywords.ListIndex
    lboxKeywords_Change
End Sub

Private Sub bttnEdit_Click()
    If lboxKeywords.ListIndex < 0 Then
        Exit Sub
    End If
    
    Dim s As String
    s = InputBox("Enter the text to search for in the layer name.", "Edit Keyword", lboxKeywords.List(lboxKeywords.ListIndex))
    s = Trim(s)
    If Trim(s) <> "" Then
        lboxKeywords.AddItem s, lboxKeywords.ListIndex
        lboxKeywords.RemoveItem lboxKeywords.ListIndex
    End If
    lboxKeywords_Change
End Sub

Private Sub bttnOK_Click()
    Dim i As Integer
    
    bIsCancel = False
    SaveData
    Set cKeywords = New Collection
    For i = 0 To lboxKeywords.ListCount - 1
        cKeywords.Add lboxKeywords.List(i)
    Next i
    
    Hide
End Sub


Private Sub lboxKeywords_Change()
    If lboxKeywords.ListIndex >= 0 Then
        bttnEdit.Enabled = True
        bttnDelete.Enabled = True
    Else
        bttnEdit.Enabled = False
        bttnDelete.Enabled = False
    End If
    
    If lboxKeywords.ListCount > 0 Then
        bttnOK.Enabled = True
    Else
        bttnOK.Enabled = False
    End If
End Sub

Private Sub UserForm_Activate()
    lboxKeywords_Change
End Sub

Private Sub UserForm_Initialize()
    bIsCancel = True
    LoadData False
End Sub

Private Sub LoadData(bIsDefault As Boolean)
    Dim c As Collection
    Dim i As Integer
        
    Set c = LoadSettings_CTRemoveEnvelopes(bIsDefault)
    
    For i = 2 To c.Count
        lboxKeywords.AddItem c(i)
    Next i
    
End Sub

Private Sub SaveData()
    Dim c As Collection
    Dim i As Integer
        
    Set c = New Collection
    
    c.Add ("1")
    
    For i = 0 To lboxKeywords.ListCount - 1
        c.Add lboxKeywords.List(i)
    Next i
    
    SaveSettings_CTRemoveEnvelopes c
End Sub

Attribute VB_Name = "ufSpaceBombControlParams"
Attribute VB_Base = "0{E62A84F9-C968-4584-A947-AE0D1D3FBBE7}{39B09B06-5330-451F-838C-3665D9BC6CD0}"
Attribute VB_GlobalNameSpace = False
Attribute VB_Creatable = False
Attribute VB_PredeclaredId = True
Attribute VB_Exposed = False
Attribute VB_TemplateDerived = False
Attribute VB_Customizable = False
Option Explicit

Public bIsCancel As Boolean

Private Sub bttnCancel_Click()
    SaveData
    
    Hide
End Sub

Private Sub bttnRun_Click()
    SaveData
    
    bIsCancel = False
    Hide
End Sub

Private Sub LoadData(bIsDefault As Boolean)
    Dim c As Collection
        
    Set c = LoadSettings_CTSpaceBomb(bIsDefault)
    If c.Count > 1 Then tbLayerName.Text = c(2)
    If c.Count > 2 Then tbManualStep.Text = c(3)
    If c.Count > 3 Then checkAutoStep.Value = c(4)
    
End Sub

Private Sub SaveData()
    Dim c As Collection
        
    Set c = New Collection
    
    c.Add ("1")
    c.Add tbLayerName.Text
    c.Add tbManualStep.Text
    c.Add checkAutoStep.Value
   
     SaveSettings_CTSpaceBomb c
End Sub

Private Sub tbManualStep_Change()
    ValidateEntry "tbManualStep"
End Sub

Private Sub UserForm_Activate()
    bIsCancel = True
    LoadData False
    bttnRun.SetFocus
End Sub

Private Function ValidateEntry(tbName As String)
    Dim i As Integer
    Dim c As String
    Dim s As String
    Dim tb As TextBox
    
    Set tb = Me(tbName)
        
    s = ""
    For i = 1 To Len(tb.Text)
        c = Mid(tb.Text, i, 1)
        If InStr("0123456789.", c) Then
            s = s & c
        End If
    Next i
    
    If s <> tb.Text Then
        tb.Text = s
    End If
End Function

Attribute VB_Name = "ufSpaceBombResults"
Attribute VB_Base = "0{5369ACA0-4751-4418-979A-5D83FE174BF5}{4B3ED0B8-82AE-4BDD-AB92-BC43F4937633}"
Attribute VB_GlobalNameSpace = False
Attribute VB_Creatable = False
Attribute VB_PredeclaredId = True
Attribute VB_Exposed = False
Attribute VB_TemplateDerived = False
Attribute VB_Customizable = False
Private Sub bttnOK_Click()
    Hide
End Sub


Private Sub UserForm_Activate()
    bttnOK.SetFocus
End Sub
